FME workspace referencing_sketchup.fmw

Parameters:
- SourceDataset_OGCKML = F:\Mestrado\Computacao\Dissertacao_Maieron\implementacao\CityGML_POA\3_roof.kmz   # Source Google KML File or URL
- DestDataset_CITYGML = F:\Mestrado\Computacao\Dissertacao_Maieron\implementacao\CityGML_POA\roof_georefenced.gml   # Destination CityGML Document

Readers:
- OGCKML_1: OGCKML from $(SourceDataset_OGCKML)

Writers:
- CITYGML_1: CITYGML to $(DestDataset_CITYGML) in TMPOA_new

AnimatedUpdate (reader OGCKML_1)
Document (reader OGCKML_1)
FlyTo (reader OGCKML_1)
Folder (reader OGCKML_1)
GroundOverlay (reader OGCKML_1)
NetworkLink (reader OGCKML_1)
PhotoOverlay (reader OGCKML_1)
Placemark (reader OGCKML_1)
    -> Reprojector
Note: returns data to the local projection system
Reprojector
    DEST = TMPOA_new
    INTERPOLATION_TYPE_NAME = Nearest Neighbor
    RASTER_CELL_SIZE = Preserve Cells
    RASTER_TOLERANCE = 0.0
    SOURCE = Read from feature
    REPROJECTED -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Offsetter
Note: adjust coordinates
Offsetter
    MODE = Cartesian Coordinate
    XOFF = 0.221
    YOFF = -0.998
    ZOFF = 2.13
    OFFSET -> SolidBuilder
SolidBuilder
    ACCUM_ATTRS_NAME = Use Attributes From One Feature
    DROP_HOLES = Yes
    GROUP_BY = _geometry_name
    HOLE_ATTR = _is_void
    SOLID -> building (writer CITYGML_1)
building (writer CITYGML_1)
    attributes: _geometry_name xml_buffer, _part_number xml_uint64, _is_void xml_char(200)
ScreenOverlay (reader OGCKML_1)
SoundCue (reader OGCKML_1)
Style (reader OGCKML_1)
StyleMap (reader OGCKML_1)
Tour (reader OGCKML_1)
TourControl (reader OGCKML_1)
Wait (reader OGCKML_1)
