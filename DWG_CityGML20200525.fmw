FME workspace DWG_CityGML20200525.fmw

Parameters:
- SourceDataset_CITYGML = F:\Mestrado\Computacao\Dissertacao_Maieron\implementacao\3DCityDB\RTG_Schulungskurs_2016\RTG_Schulungskurs_2016\Exports\CityGML\Berlin_Buiding_output2.gml   # Source CityGML File(s)
- SourceDataset_XML = F:\Mestrado\Computacao\Dissertacao_Maieron\implementacao\FME\CityFurniture_class.xml   # Source XML File(s)
- SourceDataset_CITYGML_3 = F:\Mestrado\Computacao\Dissertacao_Maieron\implementacao\FME\Exemplos\Amsterdam_LoD1\Amsterdam_LoD1.gml   # Source CityGML File(s)
- DestDataset_CITYGML = F:\Mestrado\Computacao\Dissertacao_Maieron\implementacao\CityGML_POA\2987-2-F-26   # Destination CityGML Document
- SourceDataset_SHAPEFILE = F:\Mestrado\Computacao\Dissertacao_Maieron\implementacao\shapes_poa\eixos_recorte\eixos_recorte.shp   # Source Esri Shapefile(s)
- SourceDataset_LAS_3 = ""F:\Mestrado\Computacao\Dissertacao_Maieron\implementacao\relevo\MDS-20200403T125128Z-001\MDS\2987-2-f-26.las" "F:\Mestrado\Computacao\Dissertacao_Maieron\implementacao\relevo\MDS-20200403T125128Z-001\MDS\2987-2-f-27.las" "F:\Mestrado\Computacao\Dissertacao_Maieron\implementacao\relevo\MDS-20200403T125128Z-001\MDS\2987-2-f-36.las" "F:\Mestrado\Computacao\Dissertacao_Maieron\implementacao\relevo\MDS-20200403T125128Z-001\MDS\2987-2-f-37.las""   # Source ASPRS LAS File(s)
- SourceDataset_TIFF = F:\Mestrado\Computacao\Dissertacao_Maieron\implementacao\relevo\MDT-20200403T125321Z-001\MDT\MDT_2987-2-F-I_TM-POA.tif   # Source TIFF (Tagged Image File Format) File(s)
- SourceDataset_OSM = F:\Mestrado\Computacao\Dissertacao_Maieron\implementacao\OSM\area_estudo.osm   # Source OpenStreetMap File(s)
- SourceDataset_ACAD_8 = ""F:\Mestrado\Computacao\Dissertacao_Maieron\implementacao\dwg_olimpico\2987-2-F-26.dwg" "F:\Mestrado\Computacao\Dissertacao_Maieron\implementacao\dwg_olimpico\2987-2-F-27.dwg" "F:\Mestrado\Computacao\Dissertacao_Maieron\implementacao\dwg_olimpico\2987-2-F-36.dwg" "F:\Mestrado\Computacao\Dissertacao_Maieron\implementacao\dwg_olimpico\2987-2-F-37.dwg""   # Source Autodesk AutoCAD DWG/DXF File(s)
- SourceDataset_OSM_4 = F:\Mestrado\Computacao\Dissertacao_Maieron\implementacao\OSM\poa_osm.osm   # Source OpenStreetMap File(s)
- DestDataset_INSPIRE = F:\Mestrado\Computacao\Dissertacao_Maieron\implementacao\CityGML_POA   # Destination Geography Markup Language (GML) File
- DestDataset_GML = F:\Mestrado\Computacao\Dissertacao_Maieron\implementacao\CityGML_POA\simple_grid.gml   # Destination Geography Markup Language (GML) File
- DestDataset_SHAPEFILE = F:\Mestrado\Computacao\Dissertacao_Maieron\implementacao\shapes_poa\dwg_shape\tester_passed   # Destination Esri Shapefile Folder
- DestDataset_SHAPEFILE_10 = F:\Mestrado\Computacao\Dissertacao_Maieron\implementacao\shapes_poa\dwg_shape\spatial_filter_failed   # Destination Esri Shapefile Folder

Readers:
- CITYGML_1: CITYGML from $(SourceDataset_CITYGML)
- XML_1: XML from $(SourceDataset_XML)
- CITYGML_2: CITYGML from $(SourceDataset_CITYGML_3) in EPSG:7415
- SHAPEFILE_1: SHAPEFILE from $(SourceDataset_SHAPEFILE) in TMPOA
- LAS_1: LAS from $(SourceDataset_LAS_3) in TMPOA
- TIFF_1: TIFF from $(SourceDataset_TIFF) in TMPOA
- OSM_1: OSM from $(SourceDataset_OSM) in EPSG4326
- ACAD_1: ACAD from $(SourceDataset_ACAD_8) in TMPOA
- OSM_2: OSM from $(SourceDataset_OSM_4) in LL-WGS84

Writers:
- CITYGML_3: CITYGML to $(DestDataset_CITYGML) in TMPOA
- INSPIRE_1: INSPIRE to $(DestDataset_INSPIRE) in TMPOA
- GML_1: GML to $(DestDataset_GML) in TMPOA
- SHAPEFILE_2: SHAPEFILE to $(DestDataset_SHAPEFILE) in TMPOA
- SHAPEFILE_3: SHAPEFILE to $(DestDataset_SHAPEFILE_10) in TMPOA

AttributeFilter_3
    ATTR_NAME = fme_type
    ATTR_VALUES = <Empty>,<Missing>,<Null>,<Unfiltered>,fme_area,fme_line,fme_point
Note: DTM
TIFF (reader TIFF_1)
    attributes: datatype char(255)
    -> RasterBandPropertyExtractor
    -> Junction_3
    -> Junction_5
    -> Junction_7
    -> Junction_9
    -> Junction_11
    -> Junction_13
    -> Junction_15
    -> Junction_17
    -> Junction_19
    -> SurfaceModeller [POINTS/LINES]
Note: Line_ZValue_from_Raster_3 : Raster_input
Junction_13
    -> Junction_14
Note: AttributeCreator_8 : Input
Junction_15
    -> Junction_16
Note: Clipper_3 : Clippee
Junction_17
    -> Junction_18
Note: Line_ZValue_from_Raster_2 : Raster_input
Junction_19
    -> Junction_20
Note: Clipper_2 : Clippee
Junction_3
    -> Junction_4
Note: Polygon_ZValue_from_Raster_2 : Raster_input
Junction_5
    -> Junction_6
Note: Polygon_ZValue_from_Raster : Raster_input
Junction_9
    -> Junction_10
RasterBandPropertyExtractor
    -> RasterPropertyExtractor
RasterPropertyExtractor
    -> AttributeManager_22
AttributeManager_22
    ATTR_TABLE = SET_TO gml_id = gml_@UUID()
    -> RasterCellCoercer
RasterCellCoercer
    CELL_GEOMETRY = Points
    COL_ATTR = col
    EXTRACT_BAND_VALUES_AS = Attributes
    EXTRACT_NODATA = No
    PRESERVE_ATTRIBUTES = Yes
    RASTER_ID = gml_id
    ROW_ATTR = row
    -> ElevationGridCoverage (writer INSPIRE_1)
    -> NewFeatureType (writer GML_1)
NewFeatureType (writer GML_1)
    attributes: datatype xml_char(255), _band{}.band_name xml_char(200), _band{}.band_interpretation xml_char(200), _band{}.band_bit_depth xml_char(200), _band{}.band_num_tile_rows xml_char(200), _band{}.band_num_tile_columns xml_char(200), _band{}.band_nodata xml_char(200), _band{}.band_selected xml_char(200), _band{}.band_num_palettes xml_char(200), _band{}.palette{}.palette_name xml_char(200), _band{}.palette{}.palette_key_interpretation xml_char(200), _band{}.palette{}.palette_value_interpretation xml_char(200), _band{}.palette{}.palette_bit_depth xml_char(200), _band{}.palette{}.palette_selected xml_char(200), _num_bands xml_char(200), _num_rows xml_char(200), _num_columns xml_char(200), _spacing_x xml_char(200), _spacing_y xml_char(200), _origin_x xml_char(200), _origin_y xml_char(200), _rotation_x xml_char(200), _rotation_y xml_char(200), _min_x xml_char(200), _min_y xml_char(200), _max_x xml_char(200), _max_y xml_char(200), _cell_origin_x xml_char(200), _cell_origin_y xml_char(200), _upper_left_x xml_char(200),
      _upper_left_y xml_char(200), _upper_right_x xml_char(200), _upper_right_y xml_char(200), _lower_right_x xml_char(200), _lower_right_y xml_char(200), _lower_left_x xml_char(200), _lower_left_y xml_char(200), _band{}.value xml_char(200), _band{}.palette{}.value xml_char(200), col xml_char(200), row xml_char(200)
ElevationGridCoverage (writer INSPIRE_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_role xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_role xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_role xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, identifier.Identifier.localId xml_buffer, identifier.Identifier.namespace xml_buffer, identifier.Identifier.versionId xml_buffer,
      identifier.Identifier.versionId.nilReason xml_buffer, identifier.Identifier.versionId.xsi_nil xml_boolean, metadata xml_xml, metadata.nilReason xml_buffer, metadata.gml_remoteSchema xml_buffer, metadata.xlink_href xml_buffer, metadata.xlink_role xml_buffer, metadata.xlink_title xml_buffer, metadata.owns xml_boolean, metadata.xsi_nil xml_boolean, member{}.owns xml_boolean, member{}.nilReason xml_buffer, member{}.gml_remoteSchema xml_buffer, member{}.xlink_href xml_buffer, member{}.xlink_role xml_buffer, member{}.xlink_title xml_buffer
Note: Polygon_ZValue_from_Raster_3 : Raster_input
Junction_11
    -> Junction_12
Note: Line_ZValue_from_Raster : Raster_input
Junction_7
    -> Junction_8
Building (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, OSM_id xml_buffer, _address xml_buffer, website xml_buffer
SolitaryVegetationObject (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_species xml_buffer, citygml_species_codeSpace xml_buffer, citygml_height xml_real64, citygml_height_units xml_buffer, citygml_trunk_diameter xml_real64, citygml_trunk_diameter_units xml_buffer, citygml_crown_diameter xml_real64, citygml_crown_diameter_units xml_buffer, citygml_level_of_detail{} xml_buffer
PlantCover (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_average_height xml_real64, citygml_average_height_units xml_buffer, citygml_level_of_detail{} xml_buffer
TransportationComplex (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
CityFurniture (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer
CityModel (writer CITYGML_3)
    attributes: citygml_target_uri xml_buffer, gml_description xml_buffer, gml_name xml_buffer, citygml_city_object_member{}.xlink_href xml_buffer, citygml_appearance_member{}.xlink_href xml_buffer, gml_feature_member{}.xlink_href xml_buffer
ClosureSurface (writer CITYGML_3)
    attributes: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
Building (reader CITYGML_1)
    attributes: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

Bookmark: OSM data poa
aerialway (reader OSM_2)
    attributes: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
amenity (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, shelter xml_buffer, ref xml_buffer, ele xml_buffer, gnis:feature_id xml_buffer, gnis:created xml_buffer, gnis:county_id xml_buffer, gnis:state_id xml_buffer, atm xml_buffer, backrest xml_buffer, recycling_type xml_buffer, recycling:glass xml_buffer, support xml_buffer, covered xml_buffer, bicycle_parking xml_buffer, network xml_buffer, brand xml_buffer, religion xml_buffer, wheelchair xml_buffer,
      operator:type xml_buffer, addr:housenumber xml_buffer, shelter_type xml_buffer, vending xml_buffer, sport xml_buffer, note xml_buffer, parking xml_buffer, access xml_buffer, capacity xml_buffer, cuisine xml_buffer, addr:street xml_buffer, social_facility xml_buffer, source xml_buffer, operator xml_buffer, building xml_buffer, amenity xml_buffer
    -> AttributeFilter_3
barrier (reader OSM_2)
    attributes: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
building (reader OSM_2)
    attributes: created_by xml_buffer, area xml_buffer, tag{}.k xml_buffer, tag{}.v xml_buffer, nd{}.ref xml_buffer, member{}.type xml_buffer, member{}.ref xml_buffer, member{}.role xml_buffer, osm_feature_type xml_buffer, osm_theme xml_buffer, source xml_buffer, military xml_buffer, denomination xml_buffer, ref:ruian:building xml_buffer, building:ruian:type xml_buffer, construction xml_buffer, fixme xml_buffer, tourism xml_buffer, ref:bag xml_buffer, source:date xml_buffer, religion xml_buffer, amenity xml_buffer, start_date xml_buffer, layer xml_buffer, building:use:pl xml_buffer, addr:housenumber xml_buffer, addr:city xml_buffer, addr:postcode xml_buffer, power xml_buffer, substation xml_buffer,
      building:usage:pl xml_buffer, building:levels xml_buffer, name xml_buffer, addr:street xml_buffer, height xml_buffer, building xml_buffer
    -> AttributeFilter_3
craft (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, addr:housenumber xml_buffer, craft xml_buffer
    -> AttributeFilter_3
emergency (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, fire_hydrant:type xml_buffer, fire_hydrant:diameter xml_buffer, fire_hydrant:position xml_buffer, access xml_buffer, operator xml_buffer, highway xml_buffer, name xml_buffer, foot xml_buffer, emergency xml_buffer
    -> AttributeFilter_3
highway (reader OSM_2)
    attributes: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
landuse (reader OSM_2)
    attributes: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
leisure (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, sport xml_buffer, source xml_buffer, type xml_buffer, access xml_buffer, addr:street xml_buffer, website xml_buffer, boundary xml_buffer, building xml_buffer, name xml_buffer, leisure xml_buffer
    -> AttributeFilter_3
man_made (reader OSM_2)
    attributes: created_by xml_buffer, area xml_buffer, tag{}.k xml_buffer, tag{}.v xml_buffer, nd{}.ref xml_buffer, member{}.type xml_buffer, member{}.ref xml_buffer, member{}.role xml_buffer, osm_feature_type xml_buffer, osm_theme xml_buffer, source xml_buffer, surveillance xml_buffer, surveillance:type xml_buffer, street_cabinet xml_buffer, operator xml_buffer, location xml_buffer, type xml_buffer, layer xml_buffer, tower:type xml_buffer, communication:mobile_phone xml_buffer, building xml_buffer, note xml_buffer, ref xml_buffer, ele xml_buffer, name xml_buffer, man_made xml_buffer
    -> AttributeFilter_3
military (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, building xml_buffer, bunker_type xml_buffer, historic xml_buffer, military xml_buffer
    -> AttributeFilter_3
natural (reader OSM_2)
    attributes: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
office (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, building xml_buffer, addr:housenumber xml_buffer, office xml_buffer
    -> AttributeFilter_3
power (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, source xml_buffer, ref xml_buffer, location xml_buffer, frequency xml_buffer, generator:source xml_buffer, generator:method xml_buffer, generator:output:electricity xml_buffer, cables xml_buffer, name xml_buffer, substation xml_buffer, building xml_buffer, operator xml_buffer, voltage xml_buffer, power xml_buffer
    -> AttributeFilter_3
public_transport (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, bus xml_buffer, highway xml_buffer, network xml_buffer, type xml_buffer, railway xml_buffer, operator xml_buffer, public_transport xml_buffer
    -> AttributeFilter_3
railway (reader OSM_2)
    attributes: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
route (reader OSM_2)
    attributes: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
shop (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, source xml_buffer, building xml_buffer, addr:housenumber xml_buffer, shop xml_buffer
    -> AttributeFilter_3
sport (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, leisure xml_buffer, name xml_buffer, golf xml_buffer, landuse xml_buffer, natural xml_buffer, surface xml_buffer, sport xml_buffer
    -> AttributeFilter_3
tourism (reader OSM_2)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, information xml_buffer, ele xml_buffer, artwork_type xml_buffer, addr:street xml_buffer, building xml_buffer, tourism xml_buffer
    -> AttributeFilter_3
waterway (reader OSM_2)
    attributes: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

Bookmark: buildings
Note: Schools
Escola_Publica_Privada (reader ACAD_1)
    -> AttributeManager_5
Note: Buildings holes
Edificacoes_Vazios (reader ACAD_1)
    -> CoordinateRounder
Note: Buildings
Edificacoes (reader ACAD_1)
    -> AttributeManager_9
Note: Relevant buildings
Edificacoes_Notaveis (reader ACAD_1)
    -> AttributeManager_9
CoordinateRounder
    XPREC = 2
    YPREC = 2
    ZPREC = 2
    ROUNDED -> AttributeFilter
AttributeFilter
    ATTR_NAME = fme_geometry
    ATTR_VALUES = <Empty>,<Missing>,<Null>,<Unfiltered>,fme_polygon,fme_line
    fme_polygon -> TopologyBuilder_2
    fme_polygon -> PolylineAnalyzer
    fme_polygon -> PythonCaller
    fme_line -> Chopper_2
TopologyBuilder_3
    ALLOW_CYCLES = No
    BOUNDING_EDGES = All
    CLEANING_TOLERANCE = Automatic
    DEAGGREGATE_INPUT = Yes
    GENERATION_MODE = INTERSECT
    MAX = 0
    OVERLAPPING_MODE = No
    NODE -> SpatialFilter_3 [Filter]
PolylineAnalyzer_2
    ANGLERADIUS = 2.5
    AZIMUTHRADIUS = 2
    LABELPOINTREPLACER_HEIGHT = 1
    OUTPUT_CHOICE = All
    SEGMENTANGLERADIUS = 1.5
    Vertex -> AttributeCreator_5
AttributeCreator_5
    ATTR_TABLE = SET_TO angulo = @sub(@Value(_angle_out) ,@Value(_angle_in))
    -> Tester_9
Tester_9
    BOOL_OP = COMPOSITE
    COMPOSITE_TEST = 1 AND 2
    TEST_CLAUSE:
      NUM_TEST @Value(angulo) > -0.1
      NUM_TEST @Value(angulo) < 0.1
    TEST_MODE = NUM_TEST
    PASSED -> SpatialFilter_3 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> PythonCaller_3
PythonCaller_3
    PYTHONSOURCE:
      import fme
      import fmeobjects

      class FeatureProcessor(object):
          def __init__(self):
              self.points = []
              self.polygons = []

          def input(self, feature):
              geomType = feature.getGeometryType()
              if geomType == fmeobjects.FME_GEOM_POINT:
                  self.points.append(feature)
              elif geomType == fmeobjects.FME_GEOM_POLYGON:
                  self.polygons.append(feature)

          def close(self):
              points = set([p.getCoordinate(0) for p in self.points])
              for polygon in self.polygons:
                  vertices = polygon.getAllCoordinates()
                  vertices = [p for p in vertices if p not in points]
                  if vertices[0] != vertices[-1]:
                      vertices.append(vertices[0])
                  boundary = fmeobjects.FMELine(vertices)
                  polygon.setGeometry(fmeobjects.FMEPolygon(boundary))
                  self.pyoutput(polygon)
    PYTHONSYMBOL = FeatureProcessor
    -> AreaOnAreaOverlayer [AREA]
Note: Create donuts inside buildings
AreaOnAreaOverlayer
    ACCUM_ATTRS_NAME = Use Attributes From One Feature
    CLEANING_TOLERANCE = None
    CONNECT_Z_MODE = First Wins
    DEAGGREGATE_INPUT = No
    OVC_ATTR = _overlaps
    AREA -> Tester_2
Note: Exclude holes before creating gml_id
Tester_2
    BOOL_OP = OR
    COMPOSITE_TEST = 1
    TEST_CLAUSE = TEST citygml_class_codeSpace ATTRIBUTE_HAS_A_VALUE ""
    TEST_MODE = TEST
    PASSED -> AttributeManager_8
AttributeManager_8
    ATTR_TABLE = SET_TO gml_id = gml_@UUID()
    -> AreaGapAndOverlapCleaner
AreaGapAndOverlapCleaner
    CLEANING_TOLERANCE = 0.2
    CONNECT_Z_MODE = First Wins
    DEAGGREGATE_INPUT = YES
    FILL_ALL_GAPS = No
    MEASURE_TYPE = Continuous
    MISSING_VAL_MODE = Compute
    REPAIR_METHOD = Longest Boundary
    REPAIRED -> GeometryValidator
GeometryValidator
    ISSUE_ATTR_NAME = _issues
    PRESETS = Custom
    REPAIR = Yes
    RULES = TYPE_REPAIR CONNECT_Z_MODE]FIRST_WINS]ARC_ENDPOINT_TOLERANCE_MODE]Auto]ARC_ENDPOINT_TOLERANCE]<Unused>]FME_CONTROLLER_QUERY_FILE]transformers/dependencies/geometryvalidator/TYPE_REPAIR.fme NULL_REMOVAL  SELF_INTERSECTING CHECK_HOLE_TOUCHING_POLYGON]No]CONNECT_Z_MODE_SI]FIRST_WINS]SELF_INTERSECTION_TOLERANCE]Automatic]FME_CONTROLLER_QUERY_FILE]transformers/dependencies/geometryvalidator/SELF_INTERSECTING.fme
    SUMMARY = Detailed
    PASSED -> Reprojector_3 [off]
    PASSED -> AreaCalculator_4
AreaCalculator_4
    AREA_ATTR = _area
    AREA_TYPE = Plane Area
    MULT = 1
    -> Tester_7
Tester_7
    BOOL_OP = OR
    COMPOSITE_TEST = 1
    TEST_CLAUSE = TEST @Value(_area) > 1
    TEST_MODE = TEST
    PASSED -> Counter
    PASSED -> FeatureMerger_3 [REQUESTOR] [off]
geometry_filter: AttributeFilter
    ATTR_NAME = fme_type
    ATTR_VALUES = <Empty>,<Missing>,<Null>,<Unfiltered>,fme_area,fme_line,fme_point,fme_multipolygon
    fme_area -> AttributeFilter_building
    fme_point -> Reprojector_2
AttributeFilter_building
    ATTR_NAME = building
    ATTR_VALUES = <Empty>,<Missing>,<Null>,<Unfiltered>
    <UNFILTERED> -> Reprojector
Reprojector
    DEST = TMPOA
    INTERPOLATION_TYPE_NAME = Nearest Neighbor
    RASTER_CELL_SIZE = Preserve Cells
    RASTER_TOLERANCE = 0.0
    SOURCE = LL-WGS84
    REPROJECTED -> AreaCalculator_2
AreaCalculator_2
    AREA_ATTR = _area_red
    AREA_TYPE = Plane Area
    MULT = 1
    -> CenterPointExtractor_3
CenterPointExtractor_3
    CENTX = _x_red
    CENTY = _y_red
    MODE = Center
    -> CenterPointReplacer
CenterPointReplacer
    POINTTYPE = CENTEROFGRAV
    POINT -> NeighborFinder_2 [CANDIDATE]
tester_passed (writer SHAPEFILE_2) [off]
    attributes: OSM_id char(254), timestamp char(254), tag___k char(254), tag___v char(254), military char(254), denominati char(254), ref:ruian: char(254), building:r char(254), tourism char(254), religion char(254), amenity char(254), citygml_ye char(254), building:u char(254), addr:house char(254), addr:city char(254), addr:postc char(254), power char(254), substation char(254), citygml_st char(254), gml_name char(254), addr:stree char(254), building char(254), autocad_en char(50), citygml_cl char(200), citygml_00 char(200), citygml_fu char(200), citygml_01 char(200), citygml_us char(200), citygml_02 char(200), externalRe char(200),
      external00 char(200), gml_id char(200), emergency char(254), wheelchair char(254), railway:si char(254), service char(254), leisure char(254), sport char(254), man_made char(254), website char(254), craft char(254), shop char(254), aeroway char(254), office char(254), generator: char(254), generato00 char(254), generato01 char(254), bicycle_pa char(254), parking char(254), capacity char(254), cuisine char(254), social_fac char(254), _x char(200), _y char(200), _z char(200), _address char(200), _address_j char(200), _address_t char(200), _arcgis_wk char(200), _arcgis_lo char(200),
      _arcgis_ex char(200), _elevation char(200), _elevati00 char(200), _elevati01 char(200), _latitude char(200), _longitude char(200), _postal_co char(200), _tamu_cens char(200), _tamu_ce00 char(200), _tamu_ce01 char(200), _tamu_ce02 char(200), _tamu_ce03 char(200), _tamu_ce04 char(200), _tamu_ce05 char(200), _tamu_ce06 char(200), _timezone char(200), _timezone_ char(200), _timezon00 char(200), _timezon01 char(200), address_ty char(200), street_nam char(200), street_num char(200), district_n char(200), city_name char(200), state_name char(200), postal_cod char(200), _geometry_ char(254), _part_numb number(20,0), _remnant char(200), _match_id char(200),
      _distance char(200), _angle char(200), _candidate char(200), _candida00 char(200), _closest_c char(200), _closest00 char(200), _closest_b char(200), _closest01 char(200), _area double, angulo char(200), _angle_out char(254), _azimuth_o char(254), _angle_in char(254), _azimuth_i char(254), _vertex_nu number(20,0), _angle_bet char(200), gml_descri char(200)
AttributeKeeper_3 [off]
    KEEP_ATTRS = autocad_entity_handle,citygml_class,citygml_class_codeSpace,fme_basename,gml_id,_address,_dist,_rate,_x_blue,_x_red,_y_blue,_y_red,id
    KEEP_LIST = citygml_function{} citygml_function{}.codeSpace citygml_usage{} citygml_usage{}.codeSpace externalReference{} externalReference{}.externalObject.name externalReference{}.informationSystem
    -> tester_failed (writer SHAPEFILE_2) [off]
tester_failed (writer SHAPEFILE_2) [off]
    attributes: _rate char(200), _dist char(200), autocad_en char(50), citygml_cl char(200), citygml_00 char(200), citygml_fu char(200), citygml_01 char(200), citygml_us char(200), citygml_02 char(200), externalRe char(200), external00 char(200), gml_id char(200), _address char(200), _x_blue char(200), _y_blue char(200), id char(254), _x_red char(200), _y_red char(200)
GeometryReplacer_5 [off]
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> AttributeKeeper [off]
AttributeKeeper [off]
    KEEP_ATTRS = autocad_entity_handle,citygml_class,citygml_class_codeSpace,fme_basename,gml_id,_address
    KEEP_LIST = citygml_function{} citygml_function{}.codeSpace citygml_usage{} citygml_usage{}.codeSpace externalReference{} externalReference{}.externalObject.name externalReference{}.informationSystem
    -> spatial_filter_failed (writer SHAPEFILE_3) [off]
spatial_filter_failed (writer SHAPEFILE_3) [off]
    attributes: autocad_en char(50), citygml_cl char(200), citygml_00 char(200), citygml_fu char(200), citygml_01 char(200), citygml_us char(200), citygml_02 char(200), externalRe char(200), external00 char(200), gml_id char(200), _address char(200)
Reprojector_2
    DEST = TMPOA
    INTERPOLATION_TYPE_NAME = Nearest Neighbor
    RASTER_CELL_SIZE = Preserve Cells
    RASTER_TOLERANCE = 0.0
    SOURCE = LL-WGS84
    REPROJECTED -> SpatialFilter_2 [Filter]
Note: TIFF
Junction_4
    -> Clipper_2 [CLIPPEE]
Note: Point cloud to extract buildings height
LAS (reader LAS_1)
    -> Clipper [CLIPPEE]
Aggregator_3
    ACCUM_ATTRS_NAME = Merge Incoming Attributes
    AGGREGATE_TYPE = Homogeneous Collection (If Possible)
    GROUP_BY = gml_id
    MODE = Geometry - Assemble One Level
    SEP = ,
    AGGREGATE -> MultipleGeometrySetter
MultipleGeometrySetter
    CONTAIN_INDIVID_GEOMS = Yes
    AGGREGATE -> AttributeManager_12
AttributeManager_12
    ATTR_TABLE:
      REMOVE fme_basename
      REMOVE autocad_entity_handle
      REMOVE postal_code
      REMOVE surface_parent_id{}.gml_id
      REMOVE gml_id_surface
      REMOVE _geometry_name
      REMOVE _part_number
      REMOVE _match_id
    -> Building (writer CITYGML_3)
Note: VertexExtractor : Input
Junction_27
    -> Junction_28
Note: 3DForcer_3 : Output
Junction_28
    -> VertexExtractor
VertexExtractor
    Point -> Junction_25
Note: SurfaceModeller : Points/Lines
Junction_25
    -> Junction_26
Matcher_2
    BLANK_AND_MISSING_DIFFER = No
    CHECK_TYPES_AND_ENCODINGS = No
    CNT_ATTR = _match_id
    MATCHATTRS = gml_parent_id
    MATCH_STRATEGY = Match Selected Attributes
BuildingPart (writer CITYGML_3)
    attributes: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
BuildingInstallation (writer CITYGML_3)
    attributes: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

Bookmark: Create attributes according to CityGML Building Module Specs
AttributeManager_5
    ATTR_TABLE:
      SET_TO autocad_entity_handle = @Value(autocad_entity_handle)_@Value(fme_basename)
      SET_TO citygml_class = 1100
      SET_TO citygml_class_codeSpace = http://www.sig3d.org/codelists/standard/building/2.0/_AbstractBuilding_class.xml
      SET_TO citygml_function{0} = 2070
      SET_TO citygml_function{0}.codeSpace = http://www.sig3d.org/codelists/standard/building/2.0/_AbstractBuilding_function.xml
      SET_TO citygml_usage{0} = 2070
      SET_TO citygml_usage{0}.codeSpace = http://www.sig3d.org/codelists/standard/building/2.0/_AbstractBuilding_usage.xml
      SET_TO externalReference{0}.informationSystem = ftp://ftp.procempa.com.br/../CARTAS_1000/DWG/
      SET_TO externalReference{0}.externalObject.name = urn:pmpa:oid:@Value(autocad_entity_handle)
    -> CoordinateRounder
AttributeManager_9
    ATTR_TABLE:
      SET_TO autocad_entity_handle = @Value(autocad_entity_handle)_@Value(fme_basename)
      SET_TO citygml_class
      SET_TO citygml_class_codeSpace = http://www.sig3d.org/codelists/standard/building/2.0/_AbstractBuilding_class.xml
      SET_TO citygml_function{0}
      SET_TO citygml_function{0}.codeSpace = http://www.sig3d.org/codelists/standard/building/2.0/_AbstractBuilding_function.xml
      SET_TO citygml_usage{0}
      SET_TO citygml_usage{0}.codeSpace = http://www.sig3d.org/codelists/standard/building/2.0/_AbstractBuilding_usage.xml
      SET_TO externalReference{0}.informationSystem = ftp://ftp.procempa.com.br/../CARTAS_1000/DWG/
      SET_TO externalReference{0}.externalObject.name = urn:pmpa:oid:@Value(autocad_entity_handle)
    -> CoordinateRounder

Bookmark: Create polygons from lines that are connected
Chopper_2
    DEAGGREGATE_INPUT = Deaggregate
    MAX_VERTICES = 2
    MODE = By Vertex
    REMNANT_ATTR = _remnant
    CHOPPED -> Matcher_3
    UNTOUCHED -> Matcher_3
Matcher_3
    BLANK_AND_MISSING_NAMES_TRAITS_DIFFER = No
    CHECK_COORDINATE_SYSTEMS = No
    CNT_ATTR = _match_id
    LENIENT_MATCH = Yes
    MATCH = FULL
    SINGLE_MATCHED -> LineCombiner
    NOT_MATCHED -> LineCombiner
LineCombiner
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> AreaBuilder_2
AreaBuilder_2
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = End Point Snapping
    SNAP_TOLERANCE = 2
    AREA -> AttributeFilter_5
AttributeFilter_5
    ATTR_NAME = fme_geometry
    ATTR_VALUES = <Empty>,<Missing>,<Null>,<Unfiltered>,fme_polygon
    <UNFILTERED> -> AreaOnAreaOverlayer [AREA]
    fme_polygon -> PythonCaller_3
    fme_polygon -> PolylineAnalyzer_2
    fme_polygon -> TopologyBuilder_3

Bookmark: remove redundant vertex from poligons
TopologyBuilder_2
    ALLOW_CYCLES = No
    BOUNDING_EDGES = All
    CLEANING_TOLERANCE = Automatic
    DEAGGREGATE_INPUT = Yes
    GENERATION_MODE = INTERSECT
    MAX = 0
    OVERLAPPING_MODE = No
    NODE -> SpatialFilter [Filter]
PolylineAnalyzer
    ANGLERADIUS = 2.5
    AZIMUTHRADIUS = 2
    LABELPOINTREPLACER_HEIGHT = 1
    OUTPUT_CHOICE = All
    SEGMENTANGLERADIUS = 1.5
    Vertex -> AttributeCreator_6
AttributeCreator_6
    ATTR_TABLE = SET_TO angulo = @sub(@Value(_angle_out) ,@Value(_angle_in))
    -> Tester_8
Tester_8
    BOOL_OP = COMPOSITE
    COMPOSITE_TEST = 1 AND 2
    TEST_CLAUSE:
      NUM_TEST @Value(angulo) > -1
      NUM_TEST @Value(angulo) < 1
    TEST_MODE = NUM_TEST
    PASSED -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> PythonCaller
PythonCaller
    PYTHONSOURCE:
      import fme
      import fmeobjects

      class FeatureProcessor(object):
          def __init__(self):
              self.points = []
              self.polygons = []

          def input(self, feature):
              geomType = feature.getGeometryType()
              if geomType == fmeobjects.FME_GEOM_POINT:
                  self.points.append(feature)
              elif geomType == fmeobjects.FME_GEOM_POLYGON:
                  self.polygons.append(feature)

          def close(self):
              points = set([p.getCoordinate(0) for p in self.points])
              for polygon in self.polygons:
                  vertices = polygon.getAllCoordinates()
                  vertices = [p for p in vertices if p not in points]
                  if vertices[0] != vertices[-1]:
                      vertices.append(vertices[0])
                  boundary = fmeobjects.FMELine(vertices)
                  polygon.setGeometry(fmeobjects.FMEPolygon(boundary))
                  self.pyoutput(polygon)
    PYTHONSYMBOL = FeatureProcessor
    -> AreaOnAreaOverlayer [AREA]

Bookmark: Geocodification
Reprojector_3
    DEST = EPSG:4326
    INTERPOLATION_TYPE_NAME = Nearest Neighbor
    RASTER_CELL_SIZE = Preserve Cells
    RASTER_TOLERANCE = 0.0
    SOURCE = Read from feature
    REPROJECTED -> CoordinateExtractor_2
CoordinateExtractor_2
    IND = 0
    MODE = Specify Coordinate
    X_ATTR = _x
    Y_ATTR = _y
    Z_ATTR = _z
    -> Geocoder_2
Geocoder_2
    GEOCODING_SERVICE = Bing
    THREADS = 4
    TIMEOUT = 60
    -> PythonCaller_2
PythonCaller_2
    NEW_ATTRIBUTES = address_type street_name street_number district_name city_name state_name postal_code
    PYTHONSOURCE:
      import fme
      import fmeobjects
      import http.client, urllib.parse

      def processFeature(feature):
              address= feature.getAttribute('_address')
              #print('full: ',address)
              fields = address.replace('-',',').split(',')
              #print('',fields)
              if len(fields) == 6:

                  street_name = fields[0]
                  street_number = fields[1]
                  district_name = fields[2]
                  city_name = fields[3]
                  state_name = fields[4]
                  postal_code = fields[5]
                  feature.setAttribute('street_name',street_name)
                  feature.setAttribute('street_number',street_number)
                  feature.setAttribute('district_name',district_name)
                  feature.setAttribute('city_name',city_name)
                  feature.setAttribute('state_name',state_name)
                  feature.setAttribute('postal_code',postal_code)

                  #print('splited: ',fields,'Type: ',type, 'Street Name: ',street_name,'street number: ',street_number,'District name:', district_name,'City:',city_name,'State: ',state_name,'Postal code',postal_code)
              else:
                 street_name = fields[0]
                 street_number = 'S/N'
                 district_name = fields[1]
                 city_name = fields[2]
                 state_name = fields[3]
                 postal_code = fields[4]
                 feature.setAttribute('street_name',street_name)
                 feature.setAttribute('street_number',street_number)
                 feature.setAttribute('district_name',district_name)
                 feature.setAttribute('city_name',city_name)
                 feature.setAttribute('state_name',state_name)
                 feature.setAttribute('postal_code',postal_code)
                 #print('splited: ',fields,'Type: ',type, 'Street Name: ',street_name,'street number: ',street_number,'District name:', district_name,'City:',city_name,'State: ',state_name,'Postal code',postal_code)
    PYTHONSYMBOL = processFeature
    -> FeatureMerger_3 [SUPPLIER]
FeatureMerger_3
    ATTR_ACCUM_MODE = Only Use Supplier
    JOIN_KEYS = @Value(gml_id) @Value(gml_id) AUTO
    MERGE_TYPE = Attributes Only
    PROCESS_DUPS = NO
    REJECT_NULL_MISSING_KEYS = No
    SUPPLIERS_FIRST = No
    MERGED -> Counter [off]
    MERGED -> AttributeKeeper_2

Bookmark: clean up feature (optional)
AttributeKeeper_2
    KEEP_ATTRS = address_type,city_name,district_name,state_name,street_name,street_number,gml_id,postal_code
    -> GeometryRemover_3
GeometryRemover_3
    -> XMLTemplater_2 [ROOT]

Bookmark: use xAL Address Schema
Note: create xml fragment for / citygml_address
XMLTemplater_2
    OUTPUT_XML_HEADER = Yes
    RESULT_ATTRIBUTE = citygml_address
    ROOT_QUERY_EXPR:
      <Address>
      <xalAddress>
      <xAL:AddressDetails xmlns:xAL="urn:oasis:names:tc:ciq:xsdschema:xAL:2.0">
      <xAL:Country>
      <xAL:CountryName>Brazil</xAL:CountryName>
      <xAL:AdministrativeArea Type="State">
      <xAL:AdministrativeAreaName>{fme:get-attribute("state_name")}</xAL:AdministrativeAreaName>
      <xAL:Locality Type="Town">
      <xAL:LocalityName>{fme:get-attribute("city_name")}</xAL:LocalityName>
      <xAL:Thoroughfare Type="Primary">
      <xAL:ThoroughfareNumber>{fme:get-attribute("street_number")}</xAL:ThoroughfareNumber>
      <xAL:ThoroughfareName>{fme:get-attribute("street_name")}</xAL:ThoroughfareName>
      </xAL:Thoroughfare>
      <xAL:PostalCode>
      <xAL:PostalCodeNumber>{fme:get-attribute("postal_code")}</xAL:PostalCodeNumber>
      </xAL:PostalCode>
      <xAL:DependentLocality Type="District">
      <xAL:DependentLocalityName>{fme:get-attribute("district_name")}</xAL:DependentLocalityName>
      </xAL:DependentLocality>
      </xAL:Locality>
      </xAL:AdministrativeArea>
      </xAL:Country>
      </xAL:AddressDetails>
      </xalAddress>
      </Address>
    VISIBLE_QUERY_VALIDATE = Yes
    -> AttributeManager_6

Bookmark: CityGML specific properties for address information
Note: manage relation between Buildings and its address / information (gml_aprent_id) / set CityGML specific properties
AttributeManager_6
    ATTR_TABLE:
      SET_TO citygml_feature_role = address
      RENAME_SET_VALUE gml_id > gml_parent_id
      SET_TO gml_id = gml_@UUID()
      SET_TO gml_id_address2 = #@Value(gml_id)
    -> Address (writer CITYGML_3)
    -> FeatureMerger_2 [SUPPLIER]

Bookmark: Create Address Class
Address (writer CITYGML_3)
    attributes: citygml_target_uri xml_buffer, citygml_feature_role xml_buffer, citygml_feature_role_attr_name xml_buffer, citygml_feature_role_attr_val xml_buffer, gml_description xml_buffer, gml_name xml_buffer, citygml_address xml_xml

Bookmark: Intersect with OSM data to get attributes
Counter
    CNT_ATTR = _id_blue
    DOMAIN = counter_blue
    SCOPE = Global
    START = 0
    -> AreaCalculator
AreaCalculator
    AREA_ATTR = _area_blue
    AREA_TYPE = Plane Area
    MULT = 1
    -> CenterPointExtractor
CenterPointExtractor
    CENTX = _x_blue
    CENTY = _y_blue
    MODE = Center
    -> GeometryExtractor_4
GeometryExtractor_4
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> CenterPointReplacer_2
CenterPointReplacer_2
    POINTTYPE = CENTER
    POINT -> NeighborFinder_2 [BASE]
NeighborFinder_2
    ATTR_ACCUM_MODE = Merge Candidate
    ATTR_CONFLICT_RES = Use Base
    CANDIDATES_FIRST = Yes
    INSERT_VERTEX = No
    K = 1
    MAX = 4
    MEASURES_FROM_CANDIDATE = Yes
    MEASURE_TYPE = Continuous
    MODE = Bases and Candidates
    TREAT_POLYGON_AS = Areas
    MATCHED -> GeometryReplacer_4
    UNMATCHED_BASE -> GeometryReplacer_5 [off]
    UNMATCHED_BASE -> GeometryReplacer_6
GeometryReplacer_4
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> Aggregator_4
Aggregator_4
    ACCUM_ATTRS_NAME = Get Attributes From One Representative Feature
    AGGREGATE_TYPE = Homogeneous Collection (If Possible)
    COUNT_ATTR = _aggregate_count
    GROUP_BY = _id_blue
    MODE = Geometry - Assemble One Level
    ORDERED = No
    SEP = ,
    SUM = _area_red
    AGGREGATE -> AttributeCreator
AttributeCreator
    ATTR_TABLE:
      SET_TO _rate = @Evaluate(@abs(@Value(_area_red)-@Value(_area_blue))/@Value(_area_blue))
      SET_TO _dist = @Evaluate(@hypot((@Value(_x_red)-@Value(_x_blue)),(@Value(_y_red)-@Value(_y_blue))))
    -> Tester_3
Tester_3
    BOOL_OP = COMPOSITE
    COMPOSITE_TEST = 1 AND 2
    TEST_CLAUSE:
      TEST @Value(_rate) <= 0.36
      TEST @Value(_dist) <= 5
    TEST_MODE = TEST
    PASSED -> Deaggregator_4
    FAILED -> Deaggregator_5
    FAILED -> AttributeKeeper_3 [off]
Deaggregator_4
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> clean_osm_attr
clean_osm_attr: AttributeManager
    ATTR_TABLE:
      REMOVE _rate
      REMOVE _dist
      REMOVE _id_blue
      REMOVE _area_red
      RENAME_SET_VALUE id > OSM_id
      REMOVE user
      REMOVE visible
      REMOVE created_by
      REMOVE area
      REMOVE uid
      REMOVE version
      REMOVE changeset
      REMOVE nd{}.ref
      REMOVE member{}.type
      REMOVE member{}.ref
      REMOVE member{}.role
      REMOVE osm_feature_type
      REMOVE osm_theme
      REMOVE source
      REMOVE construction
      REMOVE fixme
      REMOVE ref:bag
      REMOVE source:date
      RENAME_SET_VALUE start_date > citygml_year_of_construction
      REMOVE layer
      REMOVE building:usage:pl
      RENAME_SET_VALUE building:levels > citygml_storeys_above_ground
      RENAME_SET_VALUE name > gml_name
      REMOVE height
      REMOVE _overlaps
      REMOVE _area_blue
      REMOVE _x_blue
      REMOVE _y_blue
      REMOVE _aggregate_count
      REMOVE _x_red
      REMOVE _y_red
      REMOVE fire_hydrant:type
      REMOVE fire_hydrant:diameter
      REMOVE fire_hydrant:position
      REMOVE access
      REMOVE operator
      REMOVE highway
      REMOVE foot
      REMOVE gauge
      REMOVE electrified
      REMOVE railway:signal:position
      REMOVE tram
      REMOVE crossing
      REMOVE railway:position
      REMOVE railway:milestone:catenary_mast
      REMOVE wikipedia
      REMOVE public_transport
      REMOVE train
      REMOVE voltage
      REMOVE frequency
      REMOVE ref
      REMOVE railway
      REMOVE golf
      REMOVE landuse
      REMOVE natural
      REMOVE surface
      REMOVE surveillance
      REMOVE surveillance:type
      REMOVE street_cabinet
      REMOVE location
      REMOVE type
      REMOVE tower:type
      REMOVE communication:mobile_phone
      REMOVE note
      REMOVE ele
      REMOVE boundary
      REMOVE bus
      REMOVE network
      REMOVE cables
      REMOVE information
      REMOVE artwork_type
      REMOVE shelter
      REMOVE gnis:feature_id
      REMOVE gnis:created
      REMOVE gnis:county_id
      REMOVE gnis:state_id
      REMOVE atm
      REMOVE backrest
      REMOVE recycling_type
      REMOVE recycling:glass
      REMOVE support
      REMOVE covered
      REMOVE brand
      REMOVE operator:type
      REMOVE shelter_type
      REMOVE vending
    -> python_attribute_mapper
python_attribute_mapper: PythonCaller
    PYTHONSOURCE:
      import fme
      import fmeobjects
      import glob
      import pandas as pd
      cont=0


      def processFeature(feature):
          cont=0
          contu=0
          #feature.rename(columns={"roof:shape": "roofshape"})
          for file_name in glob.glob('F:\Mestrado\Computacao\Dissertacao_Maieron\implementacao\OSM\OSM_Building\\'+'*.csv'):
              Name = file_name.replace('F:\Mestrado\Computacao\Dissertacao_Maieron\implementacao\OSM\OSM_Building\\','').replace('.csv','')
              #print('nome csv: ' ,Name)
              x = pd.read_csv(file_name, low_memory=False)
              #print("mapa: ", x)
              osm_attr_value = feature.getAttribute(Name)
              isNull, isMissing, type = feature.getAttributeNullMissingAndType(Name)
              if isMissing ==  True:
                  #print('Atributo ' ,Name, 'da feature é Missing')
                  pass
              else:
                  function_list = feature.getAttribute('citygml_function{}')
                  usage_list = feature.getAttribute('citygml_usage{}')
                  if cont == 0:
                      func0 = feature.getAttribute('citygml_function{0}')
                      if func0 ==  '':
                          for j, valj in enumerate(x[Name]):
                                      #print('entrou no for testando: ',j, '  valor:', valj, ' function: ',function_list)
                                      if str(valj) ==  osm_attr_value:
                                          #print('entrou no if 1 testando: ',valj, 'code mapa ==',x.loc[j,'building_function_code'])
                                          if str(x.loc[j,'building_function_code']) != 'nan':
                                              feature.setAttribute('citygml_function{0}', str(x.loc[j,'building_function_code']))
                                              feature.setAttribute('citygml_usage{0}', str(x.loc[j,'building_function_code']))
                                              feature.setAttribute('citygml_class', str(x.loc[j,'building_class_code']))
                                              teste2 = feature.getAttribute('citygml_function{0}')
                                              #print('Valor destinado a função indice', cont, ': ',teste2,'OSM_ID: ',feature.getAttribute('OSM_id'))
                                              cont = cont+1
                      else:
                          cont = cont+1
                  else:
                      funcx = feature.getAttribute('citygml_function{%d}'%cont)
                      print('contador:' , cont,'citygml_function na feature:' ,funcx )
                      if str(funcx) ==  'None':
                          print('entrou no if do none')
                          for j, valj in enumerate(x[Name]):
                                  #print('entrou no for testando: ',j, '  valor:', valj, ' function: ',function_list)
                                  if str(valj) ==  osm_attr_value:
                                          print('entrou no if 11 testando: ',valj,'function anterior: ',str(feature.getAttribute('citygml_function{%d}'%(cont-1))), 'code mapa ==',str(x.loc[j,'building_function_code']))
                                          if str(x.loc[j,'building_function_code']) != 'nan':
                                              feature.setAttribute('citygml_function{%d}'%cont, str(x.loc[j,'building_function_code']))
                                              feature.setAttribute('citygml_usage{%d}'%cont, str(x.loc[j,'building_function_code']))
                                              #print('classe anterior: ',feature.getAttribute('citygml_class'))
                                              feature.setAttribute('citygml_class', str(x.loc[j,'building_class_code']))
                                              #print('classe posterior: ',feature.getAttribute('citygml_class'))
                                              teste = feature.getAttribute('citygml_function{%d}'%cont)
                                              print(' if 2 Valor destinado a função indice', cont, ': ',teste,'OSM_ID: ',feature.getAttribute('OSM_id'))
                                              cont = cont+1
    PYTHONSYMBOL = processFeature
    -> python_attribute_mapper_4
python_attribute_mapper_4: PythonCaller
    NEW_ATTRIBUTES = gml_description
    PYTHONSOURCE:
      import fme
      import fmeobjects
      import glob
      import pandas as pd
      cont=0

      def processFeature(feature):
         tags = feature.getAttribute('tag{}.k')
         for i, x in enumerate(tags):

             if feature.getAttribute('tag{%d}.k' % i) == 'description':
                 #print('entrou no if:',feature.getAttribute('tag{%d}.v' % i))
                 feature.setAttribute('gml_description', feature.getAttribute('tag{%d}.v' % i))
             if feature.getAttribute('tag{%d}.k' % i) == 'name':
                 #print('entrou no if do neme:',feature.getAttribute('tag{%d}.v' % i),'nome original:',feature.getAttribute('gml_name'))
                 if str(feature.getAttribute('gml_name'))=='None':
                     #print('entrou no if 2 do neme:',feature.getAttribute('tag{%d}.v' % i))
                     feature.setAttribute('gml_name',feature.getAttribute('tag{%d}.v' % i))
    PYTHONSYMBOL = processFeature
    -> Bufferer_2
    -> tester_passed (writer SHAPEFILE_2) [off]
    -> FeatureMerger [REQUESTOR]
Deaggregator_5
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> Bufferer_2
    DEAGGREGATED -> FeatureMerger [REQUESTOR]
GeometryReplacer_6
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> Bufferer_2
    -> FeatureMerger [REQUESTOR]

Bookmark: OSM Data study area
aerialway (reader OSM_1)
    attributes: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
aeroway (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, building xml_buffer, ele xml_buffer, surface xml_buffer, ref xml_buffer, source xml_buffer, aeroway xml_buffer
    -> geometry_filter
amenity (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, shelter xml_buffer, ref xml_buffer, ele xml_buffer, gnis:feature_id xml_buffer, gnis:created xml_buffer, gnis:county_id xml_buffer, gnis:state_id xml_buffer, atm xml_buffer, backrest xml_buffer, recycling_type xml_buffer, recycling:glass xml_buffer, support xml_buffer, covered xml_buffer, bicycle_parking xml_buffer, network xml_buffer, brand xml_buffer, religion xml_buffer, wheelchair xml_buffer,
      operator:type xml_buffer, addr:housenumber xml_buffer, shelter_type xml_buffer, vending xml_buffer, sport xml_buffer, note xml_buffer, parking xml_buffer, access xml_buffer, capacity xml_buffer, cuisine xml_buffer, addr:street xml_buffer, social_facility xml_buffer, source xml_buffer, operator xml_buffer, building xml_buffer, amenity xml_buffer
    -> geometry_filter
barrier (reader OSM_1)
    attributes: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
building (reader OSM_1)
    attributes: created_by xml_buffer, area xml_buffer, tag{}.k xml_buffer, tag{}.v xml_buffer, nd{}.ref xml_buffer, member{}.type xml_buffer, member{}.ref xml_buffer, member{}.role xml_buffer, osm_feature_type xml_buffer, osm_theme xml_buffer, source xml_buffer, military xml_buffer, denomination xml_buffer, ref:ruian:building xml_buffer, building:ruian:type xml_buffer, construction xml_buffer, fixme xml_buffer, tourism xml_buffer, ref:bag xml_buffer, source:date xml_buffer, religion xml_buffer, amenity xml_buffer, start_date xml_buffer, layer xml_buffer, building:use:pl xml_buffer, addr:housenumber xml_buffer, addr:city xml_buffer, addr:postcode xml_buffer, power xml_buffer, substation xml_buffer,
      building:usage:pl xml_buffer, building:levels xml_buffer, name xml_buffer, addr:street xml_buffer, height xml_buffer, building xml_buffer
    -> geometry_filter
craft (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, addr:housenumber xml_buffer, craft xml_buffer
    -> geometry_filter
emergency (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, fire_hydrant:type xml_buffer, fire_hydrant:diameter xml_buffer, fire_hydrant:position xml_buffer, access xml_buffer, operator xml_buffer, highway xml_buffer, name xml_buffer, foot xml_buffer, emergency xml_buffer
    -> geometry_filter
highway (reader OSM_1)
    attributes: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
landuse (reader OSM_1)
    attributes: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
leisure (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, sport xml_buffer, source xml_buffer, type xml_buffer, access xml_buffer, addr:street xml_buffer, website xml_buffer, boundary xml_buffer, building xml_buffer, name xml_buffer, leisure xml_buffer
    -> geometry_filter
man_made (reader OSM_1)
    attributes: created_by xml_buffer, area xml_buffer, tag{}.k xml_buffer, tag{}.v xml_buffer, nd{}.ref xml_buffer, member{}.type xml_buffer, member{}.ref xml_buffer, member{}.role xml_buffer, osm_feature_type xml_buffer, osm_theme xml_buffer, source xml_buffer, surveillance xml_buffer, surveillance:type xml_buffer, street_cabinet xml_buffer, operator xml_buffer, location xml_buffer, type xml_buffer, layer xml_buffer, tower:type xml_buffer, communication:mobile_phone xml_buffer, building xml_buffer, note xml_buffer, ref xml_buffer, ele xml_buffer, name xml_buffer, man_made xml_buffer
    -> geometry_filter
military (reader OSM_1)
    attributes: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
natural (reader OSM_1)
    attributes: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
office (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, building xml_buffer, addr:housenumber xml_buffer, office xml_buffer
    -> geometry_filter
power (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, source xml_buffer, ref xml_buffer, location xml_buffer, frequency xml_buffer, generator:source xml_buffer, generator:method xml_buffer, generator:output:electricity xml_buffer, cables xml_buffer, name xml_buffer, substation xml_buffer, building xml_buffer, operator xml_buffer, voltage xml_buffer, power xml_buffer
    -> geometry_filter
public_transport (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, bus xml_buffer, highway xml_buffer, network xml_buffer, type xml_buffer, railway xml_buffer, operator xml_buffer, public_transport xml_buffer
    -> geometry_filter
railway (reader OSM_1)
    attributes: created_by xml_buffer, layer xml_buffer, tag{}.k xml_buffer, tag{}.v xml_buffer, nd{}.ref xml_buffer, member{}.type xml_buffer, member{}.ref xml_buffer, member{}.role xml_buffer, osm_feature_type xml_buffer, osm_theme xml_buffer, gauge xml_buffer, electrified xml_buffer, wheelchair xml_buffer, railway:signal:direction xml_buffer, railway:signal:position xml_buffer, tram xml_buffer, highway xml_buffer, crossing xml_buffer, railway:position xml_buffer, railway:milestone:catenary_mast xml_buffer, area xml_buffer, service xml_buffer, wikipedia xml_buffer, name xml_buffer, public_transport xml_buffer, train xml_buffer, voltage xml_buffer, frequency xml_buffer, ref xml_buffer, railway xml_buffer
    -> geometry_filter
route (reader OSM_1)
    attributes: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
shop (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, source xml_buffer, building xml_buffer, addr:housenumber xml_buffer, shop xml_buffer
    -> geometry_filter
sport (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, leisure xml_buffer, name xml_buffer, golf xml_buffer, landuse xml_buffer, natural xml_buffer, surface xml_buffer, sport xml_buffer
    -> geometry_filter
tourism (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, information xml_buffer, ele xml_buffer, artwork_type xml_buffer, addr:street xml_buffer, building xml_buffer, tourism xml_buffer
    -> geometry_filter
waterway (reader OSM_1)
    attributes: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

Bookmark: Intersects with OSM points
Bufferer_2
    ANGLE = 22.5
    CAP_STYLE = Arc
    CORNER_STYLE = Arc
    MODE = AREA
    OFFSET = 1
    OFFSET_UNITS = NONE
    PRECISION = APPROX
    BUFFERED -> SpatialFilter_2 [Candidate]
SpatialFilter_2
    AGGREGATE_HANDLING = Yes
    ATTR_ACCUM_MODE = Merge Filter
    ATTR_CONFLICT_RES = Use Filter
    BASE_TYPE = Multiple Filters
    CURVE_BOUNDARY_RULE_PARAM = Default Rule
    PASS_CRITERIA = Pass Against One Filter
    PREDATTR = _predicate
    PREDICATES = INTERSECTS WITHIN TOUCHES
    USE_BOUNDING_BOX = No
    PASSED -> FeatureMerger [SUPPLIER]
FeatureMerger
    ATTR_ACCUM_MODE = Merge Supplier
    ATTR_CONFLICT_RES = Use Supplier
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> ListElementCounter
    UNMERGED_REQUESTOR -> ListDuplicateRemover_2
ListElementCounter
    CNT_ATTR = _function_count
    LIST_NAME = citygml_function{}
    -> python_attribute_mapper_2
python_attribute_mapper_2: PythonCaller
    PYTHONSOURCE:
      import fme
      import fmeobjects
      import glob
      import pandas as pd
      cont=0


      def processFeature(feature):
          cont=feature.getAttribute('_function_count')
          contu=0
          #feature.rename(columns={"roof:shape": "roofshape"})
          for file_name in glob.glob('F:\Mestrado\Computacao\Dissertacao_Maieron\implementacao\OSM\OSM_Building\\'+'*.csv'):
              Name = file_name.replace('F:\Mestrado\Computacao\Dissertacao_Maieron\implementacao\OSM\OSM_Building\\','').replace('.csv','')
              #print('nome csv: ' ,Name)
              x = pd.read_csv(file_name, low_memory=False)
              #print("mapa: ", x)
              osm_attr_value = feature.getAttribute(Name)
              isNull, isMissing, type = feature.getAttributeNullMissingAndType(Name)
              if isMissing ==  True:
                  #print('Atributo ' ,Name, 'da feature é Missing')
                  pass
              else:
                  function_list = feature.getAttribute('citygml_function{}')
                  usage_list = feature.getAttribute('citygml_usage{}')
                  if cont == 0:
                      func0 = feature.getAttribute('citygml_function{0}')
                      if func0 ==  '':
                          for j, valj in enumerate(x[Name]):
                                      #print('entrou no for testando: ',j, '  valor:', valj, ' function: ',function_list)
                                      if str(valj) ==  osm_attr_value:
                                          #print('entrou no if 1 testando: ',valj, 'code mapa ==',x.loc[j,'building_function_code'])
                                          if str(x.loc[j,'building_function_code']) != 'nan':
                                              feature.setAttribute('citygml_function{0}', str(x.loc[j,'building_function_code']))
                                              feature.setAttribute('citygml_usage{0}', str(x.loc[j,'building_function_code']))
                                              if feature.getAttribute('citygml_class') =='':
                                                 feature.setAttribute('citygml_class', str(x.loc[j,'building_class_code']))
                                              teste2 = feature.getAttribute('citygml_function{0}')
                                              #print('Valor destinado a função indice', cont, ': ',teste2,'OSM_ID: ',feature.getAttribute('OSM_id'))
                                              cont = cont+1
                      else:
                          cont = cont+1
                  else:
                      funcx = feature.getAttribute('citygml_function{%d}'%cont)
                      print('contador:' , cont,'citygml_function na feature:' ,funcx )
                      if str(funcx) ==  'None':
                          print('entrou no if do none')
                          for j, valj in enumerate(x[Name]):
                                  #print('entrou no for testando: ',j, '  valor:', valj, ' function: ',function_list)
                                  if str(valj) ==  osm_attr_value:
                                          print('entrou no if 11 testando: ',valj,'function anterior: ',str(feature.getAttribute('citygml_function{%d}'%(cont-1))), 'code mapa ==',str(x.loc[j,'building_function_code']))
                                          if str(x.loc[j,'building_function_code']) != 'nan':
                                              feature.setAttribute('citygml_function{%d}'%cont, str(x.loc[j,'building_function_code']))
                                              feature.setAttribute('citygml_usage{%d}'%cont, str(x.loc[j,'building_function_code']))
                                              #print('classe anterior: ',feature.getAttribute('citygml_class'))
                                              if feature.getAttribute('citygml_class') =='':
                                                 feature.setAttribute('citygml_class', str(x.loc[j,'building_class_code']))
                                              #print('classe posterior: ',feature.getAttribute('citygml_class'))
                                              teste = feature.getAttribute('citygml_function{%d}'%cont)
                                              print(' if 2 Valor destinado a função indice', cont, ': ',teste,'OSM_ID: ',feature.getAttribute('OSM_id'))
                                              cont = cont+1
    PYTHONSYMBOL = processFeature
    -> python_attribute_mapper_3
python_attribute_mapper_3: PythonCaller
    PYTHONSOURCE:
      import fme
      import fmeobjects
      import glob
      import pandas as pd
      cont=0


      def processFeature(feature):
         tags = feature.getAttribute('tag{}.k')
         for i, x in enumerate(tags):

             if feature.getAttribute('tag{%d}.k' % i) == 'description':
                 print('entrou no if:',feature.getAttribute('tag{%d}.v' % i))
                 feature.setAttribute('gml_description', feature.getAttribute('tag{%d}.v' % i))
             if feature.getAttribute('tag{%d}.k' % i) == 'name':
                 print('entrou no if do neme:',feature.getAttribute('tag{%d}.v' % i),'nome original:',feature.getAttribute('gml_name'))
                 if str(feature.getAttribute('gml_name'))=='None':
                     print('entrou no if 2 do neme:',feature.getAttribute('tag{%d}.v' % i))
                     feature.setAttribute('gml_name',feature.getAttribute('tag{%d}.v' % i))
    PYTHONSYMBOL = processFeature
    -> ListDuplicateRemover_2
ListDuplicateRemover_2
    SRC_LIST = citygml_function{}
    -> ListDuplicateRemover_3
ListDuplicateRemover_3
    SRC_LIST = citygml_usage{}
    -> AttributeKeeper_4
AttributeKeeper_4
    KEEP_ATTRS = autocad_entity_handle,citygml_class,citygml_class_codeSpace,fme_basename,gml_id,OSM_id,_address,citygml_storeys_above_ground,citygml_year_of_construction,gml_name,operator,website,gml_description
    KEEP_LIST = citygml_function{} citygml_function{}.codeSpace citygml_usage{} citygml_usage{}.codeSpace externalReference{} externalReference{}.externalObject.name externalReference{}.informationSystem
    -> GeometryExtractor

Bookmark: Get the ground and roof elevation from intersection with LAS and DTM (https://knowledge.safe.com/articles/1353/point-cloud-to-3d-terrain-model-with-buildings-dwg.html)
GeometryExtractor
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> Clipper [CLIPPER]
Clipper
    ATTR_ACCUM_MODE = Merge Clipper
    ATTR_CONFLICT_RES = Use Clippee
    BOUNDARY_CASES = Treat as Outside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudStatisticsCalculator
PointCloudStatisticsCalculator
    POINT_COMPONENTS = "z       MEDIAN  intensity        "
    -> AttributeManager_3
AttributeManager_3
    ATTR_TABLE = RENAME_SET_VALUE z.median > citygml_measured_height = @Format(%.2f,@Value(citygml_measured_height))
    -> Clipper_2 [CLIPPER]
Clipper_2
    ATTR_ACCUM_MODE = Merge Clipper
    ATTR_CONFLICT_RES = Use Clipper
    BOUNDARY_CASES = Treat as Inside
    CLEANING_TOLERANCE = 20
    CLIPPED_ATTR = _clipped2
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clipper and Clippee
    INSIDE -> RasterStatisticsCalculator
RasterStatisticsCalculator
    RASTER_LEVEL = BAND_ONLY
    RASTER_STATS = "0       MEDIAN "
    -> AttributeManager_4
AttributeManager_4
    ATTR_TABLE = RENAME_SET_VALUE band0.median > citygml_relative_to_water = @Format(%.2f,@Value(citygml_relative_to_water))
    -> GeometryReplacer_2
GeometryReplacer_2
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> Aggregator_2
Aggregator_2
    ACCUM_ATTRS_NAME = Merge Incoming Attributes
    AGGREGATE_TYPE = Homogeneous Collection (If Possible)
    GROUP_BY = gml_id
    MODE = Geometry - Assemble One Level
    SEP = ,
    AGGREGATE -> FeatureMerger_2 [REQUESTOR]
FeatureMerger_2
    ATTR_ACCUM_MODE = Merge Supplier
    ATTR_CONFLICT_RES = Use Requestor
    IGNORE_NULLS = No
    JOIN_KEYS = @Value(gml_id) @Value(gml_parent_id) AUTO
    LIST_ATTRS_TO_INCLUDE = gml_id
    LIST_NAME = citygml_address
    MERGE_TYPE = Attributes Only
    PROCESS_DUPS = NO
    REJECT_NULL_MISSING_KEYS = No
    SUPPLIERS_FIRST = No
    MERGED -> AttributeManager_10
    UNMERGED_REQUESTOR -> AttributeManager_10
AttributeManager_10
    ATTR_TABLE:
      REMOVE datatype
      REMOVE _clipped2
      REMOVE _clipped
      REMOVE citygml_feature_role
      REMOVE gml_parent_id
      REMOVE address_type
      REMOVE street_name
      REMOVE street_number
      REMOVE district_name
      REMOVE city_name
      REMOVE state_name
      REMOVE citygml_address
      REMOVE gml_id_address2
      RENAME_SET_VALUE citygml_address{}.gml_id > citygml_address{}.xlink_href
    -> height_filter
height_filter: Tester
    BOOL_OP = OR
    COMPOSITE_TEST = 1
    TEST_CLAUSE = TEST @Evaluate(@Evaluate(@Value(citygml_measured_height))-@Evaluate(@Value(citygml_relative_to_water))) > 2
    TEST_MODE = TEST
    PASSED -> Orientor
Orientor
    KIND = LEFT_HAND_RULE
    ORIENTED -> 3DForcer_3
3DForcer_3
    KEEPZVAL = No
    ZVALATTR = @Value(citygml_relative_to_water)
    -> Deaggregator_2
    -> CityGMLGeometrySetter
    -> Junction_27

Bookmark: Transportation
Note: TIFF
Junction_14
    -> Line_ZValue_from_Raster_3 [Raster_input]
eixos_recorte (reader SHAPEFILE_1)
    attributes: OBJECTID long, CDLOG long, CDSEG long, NRIMPINI long, NRIMPFIN long, NRPARINI long, NRPARFIN long, MTORIGEM char(20), MTQUAL char(10), CDTIPO long, MTVETOR char(26), FGCOMP double, SEL long, LABEL long, CDIDELOG long, NMIDELOG char(37), CDIDECAT char(5), NMIDEPRE char(3), NMIDEABR char(16), GEOM_LEN double
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryPropertySetter_2
GeometryPropertySetter_2
    GEOM_NAME_FIELD = fme_line
    OVERWRITE_CHOICE = Yes
    SETTYPE_PARAM = Geometry Name
    SET -> AttributeFilter_2
    SET -> AttributeCreator_18
Note: set gml_id, external reference and code_Spaces to Transportation complex
AttributeCreator_18
    ATTR_TABLE:
      SET_TO gml_id = gml_@UUID()
      SET_TO citygml_class
      SET_TO citygml_class_codeSpace = http://www.sig3d.org/codelists/standard/transportation/2.0/TransportationComplex_class.xml
      SET_TO citygml_function{0}
      SET_TO citygml_function{0}.codeSpace = http://www.sig3d.org/codelists/standard/transportation/2.0/TransportationComplex_function.xml
      SET_TO citygml_usage{0}
      SET_TO citygml_usage{0}.codeSpace = http://www.sig3d.org/codelists/standard/transportation/2.0/TransportationComplex_usage.xml
      SET_TO externalReference{0}.informationSystem = http://lproweb.procempa.com.br/pmpa/prefpoa/spm/usu_doc/eixoslogradouros.zip
      SET_TO externalReference{0}.externalObject.uri = urn:pmpa:oid:@Value(OBJECTID)
    -> AttributeValueMapper
Note: maps originals attributes to transportation complex classes codeSpace
AttributeValueMapper
    DEFAULT_VALUE = 1090
    DIRECTION = Forward (Source To Destination)
    LUT = AC,1040,AL,1040,AR,1070,AS,1040,AV,1040,BC,1010,BV,,CA,1040,CICL,1010,CN,1040,DIR,,ESC,1010,ESP,,EST,1010,ESTR,1040,GAL,1010,I,,JAR,,LAGO,,LE,,LG,,MER,1010,PCA,,PRQ,,PSG,1010,PSL,1010,R,1040,RIO,1070,RP,1010,RTL,1040,TERM,1010,TRAV,1040,TRVS,1040,TUN,,VA,1040,VDT,1040,VE,,VIA,1040,VP,1040,VTC,1010
    SRC = CDIDECAT
    VAL_ATTR = citygml_class{0}
    -> Tester
Tester
    BOOL_OP = OR
    COMPOSITE_TEST = 1
    TEST_CLAUSE = TEST citygml_class{0} ATTRIBUTE_HAS_A_VALUE ""
    TEST_MODE = TEST
    PASSED -> Line_ZValue_from_Raster_3 [Line_input]
Line_ZValue_from_Raster_3
    GML_ID = @Value(gml_id)
    -> AttributeValueMapper_2
    -> Junction_43
Note: maps originals attributes to transportation complex function codeSpace
AttributeValueMapper_2
    DEFAULT_VALUE = 2700
    DIRECTION = Forward (Source To Destination)
    LUT = AC,1280,AL,1210,AR,2620,AS,1210,AV,1210,BC,1220,BV,,CA,1210,CICL,1240,CN,1210,DIR,,ESC,1220,ESP,,EST,1920,ESTR,1000,GAL,1500,I,,JAR,,LAGO,,LE,,LG,,MER,1620,PCA,,PRQ,,PSG,1220,PSL,1220,R,1210,RIO,2622,RP,1220,RTL,1110,TERM,1920,TRAV,1220,TRVS,1220,TUN,,VA,1210,VDT,1210,VE,,VIA,1210,VP,1220,VTC,1220
    SRC = CDIDECAT
    VAL_ATTR = citygml_function{0}
    -> AttributeValueMapper_3
Note: maps originals attributes to transportation complex usage codeSpace
AttributeValueMapper_3
    DEFAULT_VALUE = 2700
    DIRECTION = Forward (Source To Destination)
    LUT = AC,1280,AL,1210,AR,2620,AS,1210,AV,1210,BC,1220,BV,,CA,1210,CICL,1240,CN,1210,DIR,,ESC,1220,ESP,,EST,1920,ESTR,1000,GAL,1500,I,,JAR,,LAGO,,LE,,LG,,MER,1620,PCA,,PRQ,,PSG,1220,PSL,1220,R,1210,RIO,2622,RP,1220,RTL,1110,TERM,1920,TRAV,1220,TRVS,1220,TUN,,VA,1210,VDT,1210,VE,,VIA,1210,VP,1220,VTC,1220
    SRC = CDIDECAT
    VAL_ATTR = citygml_usage{0}
    -> AttributeManager_7
AttributeManager_7
    ATTR_TABLE:
      REMOVE OBJECTID
      REMOVE CDLOG
      REMOVE CDSEG
      REMOVE NRIMPINI
      REMOVE NRIMPFIN
      REMOVE NRPARINI
      REMOVE NRPARFIN
      REMOVE MTORIGEM
      REMOVE MTQUAL
      REMOVE CDTIPO
      REMOVE MTVETOR
      REMOVE FGCOMP
      REMOVE SEL
      REMOVE LABEL
      REMOVE CDIDELOG
      RENAME_SET_VALUE NMIDELOG > gml_name
      REMOVE CDIDECAT
      REMOVE NMIDEPRE
      REMOVE NMIDEABR
      REMOVE GEOM_LEN
    -> CityGMLGeometrySetter_10
CityGMLGeometrySetter_10
    GEOM = lod0Network
    ROLE = cityObjectMember
    -> TransportationComplex (writer CITYGML_3)
Note: VertexExtractor_4 : Input
Junction_43
    -> Junction_44
Note: Line_ZValue_from_Raster_3 : Output
Junction_44
    -> VertexExtractor_4
VertexExtractor_4
    Point -> Junction_41
Note: SurfaceModeller : Points/Lines
Junction_41
    -> Junction_42
AttributeFilter_2
    ATTR_NAME = CDIDECAT
    ATTR_VALUES = <Empty>,<Missing>,<Null>,<Unfiltered>,AC,AL,AR,AS,AV,BC,BV,CA,CICL,CN,DIR,ESC,ESP,EST,ESTR,GAL,I,JAR,LAGO,LE,LG,MER,PCA,PRQ,PSG,PSL,R,RIO,RP,RTL,TERM,TRAV,TRVS,TUN,VA,VDT,VE,VIA,VP,VTC
    LAGO -> Junction_21
    RIO -> Junction_23
Note: AttributeCreator_2 : Input
Junction_21
    -> Junction_22
Note: AttributeManager_25 : Input
Junction_23
    -> Junction_24
Pavimentacao_Asfaltica_Mfio (reader ACAD_1)
    -> AttributeManager_14
    -> AttributeCreator_15
Pavimentacao_Nao_Asfaltica_Mfio (reader ACAD_1)
    -> AttributeManager_14
    -> AttributeCreator_17
AttributeManager_14
    ATTR_TABLE:
      SET_TO gml_id = gml_@UUID()
      SET_TO autocad_entity_handle = @Value(autocad_entity_handle)_@Value(fme_basename)
      SET_TO citygml_function{0} = 1220
      SET_TO citygml_function{0}.codeSpace = http://www.sig3d.org/codelists/standard/transportation/2.0/AuxiliaryTrafficArea_function.xml
      SET_TO externalReference{0}.informationSystem = ftp://ftp.procempa.com.br/../CARTAS_1000/DWG/
      SET_TO externalReference{0}.externalObject.name = urn:pmpa:oid:@Value(autocad_entity_handle)
Pavimentacao_Asfaltica_S_Mfio (reader ACAD_1)
    -> AttributeCreator_17
    -> AttributeCreator_15
AttributeCreator_15
    ATTR_TABLE:
      SET_TO citygml_class = road traffic
      SET_TO citygml_class_codeSpace = 1040
      SET_TO citygml_function{0} = driving_lane
      SET_TO citygml_function{0}.codeSpace = 1
      SET_TO gml_id = UUID_@UUID()
      SET_TO citygml_surface_material = asphalt
      SET_TO citygml_surface_material_codeSpace = 1
      SET_TO citygml_usage{0} = car, truck, bus, taxi, motorcycle
      SET_TO citygml{0}.codeSpace = 2,3,4,7
    -> Snapper_2
Snapper_2
    EXTEND_LINES = ALWAYS
    SAVE_SHORT_LINES = No
    SNAPTYPE_PARAM = End Point Snapping
    TOLERANCE = 20
    SNAPPED -> AreaBuilder
AttributeCreator_17
    ATTR_TABLE:
      SET_TO citygml_class = road traffic
      SET_TO citygml_class_codeSpace = 1040
      SET_TO citygml_function{0} = driving_lane
      SET_TO citygml_function{0}.codeSpace = 1
      SET_TO gml_id = UUID_@UUID()
      SET_TO citygml_surface_material = pavement
      SET_TO citygml_surface_material_codeSpace = 3
      SET_TO citygml_usage{0} = car, truck, bus, taxi, motorcycle
      SET_TO citygml_usage{0}.codeSpace = 2,3,4,7
    -> Snapper
Snapper
    EXTEND_LINES = ALWAYS
    GROUP_BY = citygml_surface_material
    SAVE_SHORT_LINES = Yes
    SNAPTYPE_PARAM = End Point Snapping
    TOLERANCE = 20
    SNAPPED -> AreaBuilder
    UNTOUCHED -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = NO
    LINES_AS_SEGMENTS = No
    POLY_ACCUM_ATTRS_NAME = Use Attributes From One Feature
    SNAPTYPE_PARAM = None
Rotula (reader ACAD_1)
Nao_Pavimentada_S_Mfio (reader ACAD_1)
Separ_Fisico_Canteiro_Mureta (reader ACAD_1)
Pavimentacao_Nao_Asfaltica_S_Mfio (reader ACAD_1)
AttributeCreator_14
    ATTR_TABLE:
      SET_TO citygml_class = road traffic
      SET_TO citygml_class_codeSpace = 1040
      SET_TO citygml_function{0} = kerbstone
      SET_TO citygml_function{0}.codeSpace = 1220
      SET_TO citygml_surface_material = concrete
      SET_TO citygml_surface_material_codeSpace = 2
    -> AuxiliaryTrafficArea (writer CITYGML_3)
AuxiliaryTrafficArea (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer
Road (writer CITYGML_3)
    attributes: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
Railway (writer CITYGML_3)
    attributes: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
Track (writer CITYGML_3)
    attributes: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
Square (writer CITYGML_3)
    attributes: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
TrafficArea (writer CITYGML_3)
    attributes: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

Bookmark: Relief
Note: TIFF
Junction_16
    -> AttributeCreator_8 [off]
Note: VertexExtractor : Point
Junction_26
    -> SurfaceModeller [POINTS/LINES] [off]
Note: VertexExtractor_3 : Point
Junction_40
    -> SurfaceModeller [POINTS/LINES] [off]
Note: VertexExtractor_4 : Point
Junction_42
    -> SurfaceModeller [BREAKLINES] [off]
Note: VertexExtractor_2 : Point
Junction_34
    -> SurfaceModeller [BREAKLINES] [off]
Curvas_Intermediarias (reader ACAD_1)
    -> 3DForcer
Curvas_Mestras (reader ACAD_1)
    -> 3DForcer
3DForcer
    KEEPZVAL = No
    ZVALATTR = @Value(autocad_elevation)
    -> SurfaceModeller [BREAKLINES]
Topon_Pto_Cotado (reader ACAD_1)
    -> SurfaceModeller [POINTS/LINES] [off]
SurfaceModeller
    ADDZ_TYPE = Replace Z
    CONTOUR_DIMENSION = 3
    CONTOUR_INTERVAL = 1
    DRAPE_TYPE = VERTEX
    IGNORE_INPUT_ON_INTERVAL = Perturb Input Points On Contour Interval
    INTERPOLATION_TYPE = AUTO
    NODATA_VALUE = -32767.0
    TOLERANCE = 1
    X_SPACING = 0.5
    Y_SPACING = 0.5
    TINSurface -> AttributeCreator_8
AttributeCreator_8
    ATTR_TABLE = SET_TO gml_id = UUID_@UUID()
    -> GeometryRemover
    -> AttributeManager
AttributeManager
    ATTR_TABLE:
      RENAME_SET_VALUE gml_id > gml_parent_id
      SET_TO citygml_level_of_detail = 1
      SET_TO gml_id = @Value(gml_parent_id)_1
      SET_TO citygml_diffuse_color = (165 42 42)
    -> CityGMLGeometrySetter_11 [off]
    -> CityGMLGeometrySetter_4
CityGMLGeometrySetter_11
    GEOM = grid
    ROLE = reliefComponent
    -> Aggregator
CityGMLGeometrySetter_4
    GEOM = tin
    ROLE = reliefComponent
    -> Aggregator
Aggregator
    ACCUM_ATTRS_NAME = Merge Incoming Attributes
    AGGREGATE_TYPE = Homogeneous Collection (If Possible)
    GROUP_BY = gml_parent_id
    MODE = Geometry - Assemble One Level
    SEP = ,
    AGGREGATE -> GeometryPropertySetter
GeometryPropertySetter
    OVERWRITE_CHOICE = Yes
    REMOVE_ATTRIBUTE = No
    SETTYPE_PARAM = Traits From Attributes
    SRC_ATTRS = citygml_lod_name
    SET -> TINRelief (writer CITYGML_3)
TINRelief (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer
GeometryRemover
    -> AttributeCreator_9
AttributeCreator_9
    ATTR_TABLE = SET_TO citygml_level_of_detail = 1
    -> ReliefFeature (writer CITYGML_3)
ReliefFeature (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_relief_component{}.xlink_href xml_buffer
BreaklineRelief (writer CITYGML_3)
    attributes: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
MassPointRelief (writer CITYGML_3)
    attributes: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
RasterRelief (writer CITYGML_3)
    attributes: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

Bookmark: WaterBody
Note: TIFF
Junction_18
    -> Clipper_3 [CLIPPEE]
Note: TIFF
Junction_20
    -> Line_ZValue_from_Raster_2 [Raster_input]
Note: AttributeFilter_2 : LAGO
Junction_22
    -> AttributeCreator_2
AttributeCreator_2
    ATTR_TABLE:
      SET_TO externalReference{0}.informationSystem = http://lproweb.procempa.com.br/pmpa/prefpoa/spm/usu_doc/eixoslogradouros.zip
      SET_TO externalReference{0}.externalObject.uri = urn:pmpa:oid:@Value(OBJECTID)
      SET_TO gml_id = gml_@UUID()
    -> AreaBuilder_4
AreaBuilder_4
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    POLY_DIRECTION = direction
    POLY_LIST_ATTRS_TO_INCLUDE_MODE = Selected Attributes
    SNAPTYPE_PARAM = None
    SNAP_TOLERANCE = 0
    AREA -> AttributeManager_2
Note: AttributeFilter_2 : RIO
Junction_24
    -> AttributeManager_25
AttributeManager_25
    ATTR_TABLE:
      SET_TO gml_id = gml_@UUID()
      SET_TO citygml_class = 1030
      SET_TO citygml_class_codeSpace = http://www.sig3d.org/codelists/standard/waterbody/2.0/WaterBody_class.xml
      SET_TO citygml_function{0} = 9999
      SET_TO citygml_function{0}.codeSpace = http://www.sig3d.org/codelists/standard/waterbody/2.0/WaterBody_function.xml
      SET_TO citygml_usage{0} = 9999
      SET_TO citygml_usage{0}.codeSpace = http://www.sig3d.org/codelists/standard/waterbody/2.0/WaterBody_usage.xml
      SET_TO externalReference{0}.informationSystem = http://lproweb.procempa.com.br/pmpa/prefpoa/spm/usu_doc/eixoslogradouros.zip
      SET_TO externalReference{0}.externalObject.name = urn:pmpa:oid:@Value(OBJECTID)
      REMOVE CDLOG
      REMOVE CDSEG
      REMOVE NRIMPINI
      REMOVE NRIMPFIN
      REMOVE NRPARINI
      REMOVE NRPARFIN
      REMOVE MTORIGEM
      REMOVE MTQUAL
      REMOVE CDTIPO
      REMOVE MTVETOR
      REMOVE FGCOMP
      REMOVE SEL
      REMOVE LABEL
      REMOVE CDIDELOG
      REMOVE NMIDELOG
      REMOVE CDIDECAT
      REMOVE NMIDEPRE
      REMOVE NMIDEABR
      REMOVE GEOM_LEN
      REMOVE fme_geometry
      REMOVE fme_type
      REMOVE _geometry_name
      REMOVE _part_number
    -> Line_ZValue_from_Raster_2 [Line_input]
Rio_Perene (reader ACAD_1)
    -> Snapper_3
Snapper_3
    EXTEND_LINES = NEVER
    SAVE_SHORT_LINES = No
    SNAPTYPE_PARAM = End Point Snapping
    TOLERANCE = 1
    SNAPPED -> LineCombiner_3
    UNTOUCHED -> LineCombiner_3
LineCombiner_3
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> AttributeManager_13
AttributeManager_13
    ATTR_TABLE:
      SET_TO gml_id = gml_@UUID()
      SET_TO autocad_entity_handle = @Value(autocad_entity_handle)_@Value(fme_basename)
      SET_TO citygml_class = 1020
      SET_TO citygml_class_codeSpace = http://www.sig3d.org/codelists/standard/waterbody/2.0/WaterBody_class.xml
      SET_TO citygml_function{0} = 9999
      SET_TO citygml_function{0}.codeSpace = http://www.sig3d.org/codelists/standard/waterbody/2.0/WaterBody_function.xml
      SET_TO citygml_usage{0} = 9999
      SET_TO citygml_usage{0}.codeSpace = http://www.sig3d.org/codelists/standard/waterbody/2.0/WaterBody_usage.xml
      SET_TO externalReference{0}.informationSystem = ftp://ftp.procempa.com.br/../CARTAS_1000/DWG/
      SET_TO externalReference{0}.externalObject.name = urn:pmpa:oid:@Value(autocad_entity_handle)
    -> GeometryExtractor_3
GeometryExtractor_3
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> Chopper
Chopper
    DEAGGREGATE_INPUT = Deaggregate
    MAX_VERTICES = 1
    MODE = By Vertex
    REMNANT_ATTR = _remnant
    CHOPPED -> NeighborFinder [CANDIDATE]
NeighborFinder
    CANDIDATES_FIRST = No
    CLOSE_LIST_ATTRS_TO_INCLUDE_MODE = All Attributes
    CLOSE_LIST_NAME = _candidate_list
    INSERT_VERTEX = No
    K = 1
    MAX = 300
    MEASURES_FROM_CANDIDATE = Yes
    MEASURE_TYPE = Continuous
    MODE = Candidates Only
    TREAT_POLYGON_AS = Lines
    MATCHED -> Tester_4
Tester_4
    BOOL_OP = OR
    COMPOSITE_TEST = 1
    TEST_CLAUSE = TEST @Value(_candidate_list{0}.gml_id) != @Value(gml_id)
    TEST_MODE = TEST
    PASSED -> StatisticsCalculator
StatisticsCalculator
    CALCULATION_MODE = NUMERIC
    FEAT_STATS = _distance,,MAX,,,MEAN,,,,,,,
    COMPLETE -> GeometryReplacer
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> Aggregator_8
Aggregator_8
    ACCUM_ATTRS_NAME = Use Attributes From One Feature
    AGGREGATE_TYPE = Homogeneous Collection (If Possible)
    GROUP_BY = gml_id
    MODE = Geometry - Assemble One Level
    ORDERED = No
    SEP = ,
    AGGREGATE -> Intersector
    AGGREGATE -> Bufferer
Bufferer
    ANGLE = 22.5
    CAP_STYLE = None
    CORNER_STYLE = Arc
    MODE = AREA
    OFFSET = @Value(_distance.max)
    OFFSET_UNITS = METERS
    PRECISION = APPROX
    BUFFERED -> Dissolver
Dissolver
    ACCUM_INPUT_ATTRS = Use Attributes From One Feature
    CLEANING_TOLERANCE = Automatic
    CONNECT_Z_MODE = First Wins
    DEAGGREGATE_INPUT = Yes
    AREA -> Intersector
Intersector
    ATTRS_ACCUM_MODE = Use Attributes From One Feature
    CLEANING_TOLERANCE = Automatic
    DEAGGREGATE_INPUT = Yes
    DUPLICATE_Z_NODES = No
    GENERATE_LIST_DROP = NO
    MEASURE_TYPE = Continuous
    NODE_NUM_ATTR = _node_number
    OV_ATTR = _overlaps
    PERFORM_SELF_INTERSECTION = No
    SEG_ATTR = _segments
    SEPARATE_COLLINEAR_SEGMENTS = No
    INTERSECTED -> PointOnLineOverlayer [LINE]
    NODE -> PointOnLineOverlayer [POINT]
PointOnLineOverlayer
    DEAGGREGATE_INPUT = Yes
    MEASURE_TYPE = Continuous
    MERGE_MEASURES = Yes
    OV_ATTR = _overlaps2
    TOLERANCE = 0.2
    LINE -> Tester_5
Tester_5
    BOOL_OP = OR
    COMPOSITE_TEST = 1
    TEST_CLAUSE = TEST @Value(_overlaps) > 3
    TEST_MODE = TEST
    PASSED -> AreaBuilder_6
    FAILED -> Tester_6
Tester_6
    BOOL_OP = OR
    COMPOSITE_TEST = 1
    TEST_CLAUSE = TEST @Length() < 20
    TEST_MODE = TEST
    PASSED -> AreaBuilder_6
AreaBuilder_6
    ALLOW_CYCLES = No
    CHECK_CURVE_DIRECTION = No
    CONNECT_Z_MODE = First Wins
    CONSIDER_NODE_ELEVATION = no
    DEAGGREGATE_INPUT = Deaggregate
    DONUT_CREATION = NO
    LINES_AS_SEGMENTS = No
    POLY_ACCUM_ATTRS_NAME = Use Attributes From One Feature
    POLY_DIRECTION = direction
    POLY_LIST_ATTRS_TO_INCLUDE = gml_id
    POLY_LIST_ATTRS_TO_INCLUDE_MODE = Selected Attributes
    POLY_LIST_NAME = child_id
    SNAPTYPE_PARAM = End Point Snapping
    SNAP_TOLERANCE = 1
    AREA -> AttributeManager_29
AttributeManager_29
    ATTR_TABLE:
      REMOVE externalReference{}.informationSystem
      REMOVE externalReference{}.externalObject.name
      REMOVE _remnant
      REMOVE _candidate_list{}.autocad_entity_handle
      REMOVE _candidate_list{}.fme_basename
      REMOVE _candidate_list{}.citygml_class
      REMOVE _candidate_list{}.citygml_class_codeSpace
      REMOVE _candidate_list{}.citygml_function{}
      REMOVE _candidate_list{}.citygml_function{}.codeSpace
      REMOVE _candidate_list{}.citygml_usage{}
      REMOVE _candidate_list{}.citygml_usage{}.codeSpace
      REMOVE _candidate_list{}.externalReference{}.informationSystem
      REMOVE _candidate_list{}.externalReference{}.externalObject.name
      REMOVE _candidate_list{}._geometry
      REMOVE _candidate_list{}._remnant
      REMOVE _distance
      REMOVE _angle
      REMOVE _candidate_angle
      REMOVE _candidate_label_angle
      REMOVE _closest_candidate_x
      REMOVE _closest_candidate_y
      REMOVE _closest_base_x
      REMOVE _closest_base_y
      REMOVE _candidate_list{}.distance
      REMOVE _candidate_list{}.angle
      REMOVE _candidate_list{}.candidate_angle
      REMOVE _candidate_list{}.candidate_label_angle
      REMOVE _candidate_list{}.closest_candidate_x
      REMOVE _candidate_list{}.closest_candidate_y
      REMOVE _candidate_list{}.closest_base_x
      REMOVE _candidate_list{}.closest_base_y
      REMOVE _distance.max
      REMOVE _distance.mean
      SET_TO _candidate_list{1}.gml_id = @Value(gml_id)
    -> ListRenamer
ListRenamer
    LEAVE_ORIG = No
    LIST_ACTION = Rename
    LIST_COMPONENT_NAMES = _candidate_list{},child_id{},gml_id,gml_id
    LIST_NAME = _candidate_list{}.gml_id
    -> AttributeManager_30
AttributeManager_30
    ATTR_TABLE = SET_TO gml_id = gml_@UUID()
    -> AttributeKeeper_5
AttributeKeeper_5
    KEEP_ATTRS = citygml_class,citygml_class_codeSpace,gml_id
    KEEP_LIST = child_id{} child_id{}.gml_id citygml_function{} citygml_function{}.codeSpace citygml_usage{} citygml_usage{}.codeSpace
    -> CenterLineReplacer
CenterLineReplacer
    MODE = Approximate Center Line
Rio_Intermitente (reader ACAD_1)
    -> LineCombiner_2
LineCombiner_2
    ACCUM_ATTRS_NAME = Use Attributes From One Feature
    BREAK = no
    CONNECT_Z_MODE = First Wins
    CONSIDER_NODE_ELEVATION = no
    DEAGGREGATE_GEOMETRY = Deaggregate
    DIRECTION_NAME = direction
    JUNCTIONS_IGNORE_ATTRIBUTES = No
    LINES_AS_SEGMENTS = No
    PRESERVE = no
    TOPOLOGY = End noded
    LINE -> AttributeManager_15
AttributeManager_15
    ATTR_TABLE:
      SET_TO gml_id = gml_@UUID()
      SET_TO autocad_entity_handle = @Value(autocad_entity_handle)_@Value(fme_basename)
      SET_TO citygml_class = 1130
      SET_TO citygml_class_codeSpace = http://www.sig3d.org/codelists/standard/waterbody/2.0/WaterBody_class.xml
      SET_TO citygml_function{0} = 9999
      SET_TO citygml_function{0}.codeSpace = http://www.sig3d.org/codelists/standard/waterbody/2.0/WaterBody_function.xml
      SET_TO citygml_usage{0} = 9999
      SET_TO citygml_usage{0}.codeSpace = http://www.sig3d.org/codelists/standard/waterbody/2.0/WaterBody_usage.xml
      SET_TO externalReference{0}.informationSystem = ftp://ftp.procempa.com.br/../CARTAS_1000/DWG/
      SET_TO externalReference{0}.externalObject.name = urn:pmpa:oid:@Value(autocad_entity_handle)
    -> Line_ZValue_from_Raster_2 [Line_input]
Line_ZValue_from_Raster_2
    GML_ID = @Value(gml_id)
    -> Aggregator_6
    -> VertexExtractor_5
VertexExtractor_5
    Point -> SurfaceModeller [BREAKLINES]
Aggregator_6
    ACCUM_ATTRS_NAME = Use Attributes From One Feature
    AGGREGATE_TYPE = Homogeneous Collection (If Possible)
    GROUP_BY = gml_id
    MODE = Geometry - Assemble One Level
    SEP = ,
    AGGREGATE -> CityGMLGeometrySetter_7
CityGMLGeometrySetter_7
    GEOM = lod0MultiCurve
    ROLE = cityObjectMember
    -> WaterBody (writer CITYGML_3)
Lagos_Lagoas (reader ACAD_1)
Lagos_Lagoas_Hatch (reader ACAD_1)
    -> AttributeManager_23
AttributeManager_23
    ATTR_TABLE:
      SET_TO gml_id = gml_@UUID()
      SET_TO autocad_entity_handle = @Value(autocad_entity_handle)_@Value(fme_basename)
      SET_TO externalReference{0}.informationSystem = ftp://ftp.procempa.com.br/../CARTAS_1000/DWG/
      SET_TO externalReference{0}.externalObject.name = urn:pmpa:oid:@Value(autocad_entity_handle)
      REMOVE autocad_elevation
      REMOVE autocad_viewport_ucs_elevation
    -> AttributeManager_2
AttributeManager_2
    ATTR_TABLE:
      SET_TO citygml_class = 1060
      SET_TO citygml_class_codeSpace = http://www.sig3d.org/codelists/standard/waterbody/2.0/WaterBody_class.xml
      SET_TO citygml_function{0} = 9999
      SET_TO citygml_function{0}.codeSpace = http://www.sig3d.org/codelists/standard/waterbody/2.0/WaterBody_function.xml
      SET_TO citygml_usage{0} = 9999
      SET_TO citygml_usage{0}.codeSpace = http://www.sig3d.org/codelists/standard/waterbody/2.0/WaterBody_usage.xml
      REMOVE OBJECTID
      RENAME_SET_VALUE CDLOG
      REMOVE CDSEG
      REMOVE NRIMPINI
      REMOVE NRIMPFIN
      REMOVE NRPARINI
      REMOVE NRPARFIN
      REMOVE MTORIGEM
      REMOVE MTQUAL
      REMOVE CDTIPO
      REMOVE MTVETOR
      REMOVE FGCOMP
      REMOVE SEL
      REMOVE LABEL
      REMOVE CDIDELOG
      REMOVE NMIDELOG
      REMOVE CDIDECAT
      REMOVE NMIDEPRE
      REMOVE NMIDEABR
      REMOVE GEOM_LEN
      REMOVE fme_geometry
      REMOVE fme_type
      REMOVE _geometry_name
      REMOVE _part_number
    -> GeometryExtractor_2
GeometryExtractor_2
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> Clipper_3 [CLIPPER]
Clipper_3
    ATTR_ACCUM_MODE = Merge Clipper
    ATTR_CONFLICT_RES = Use Clipper
    BOUNDARY_CASES = Treat as Inside
    CLEANING_TOLERANCE = 20
    CLIPPED_ATTR = _clipped2
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clipper and Clippee
    INSIDE -> RasterStatisticsCalculator_2
RasterStatisticsCalculator_2
    RASTER_LEVEL = BAND_ONLY
    RASTER_STATS = "0       MEDIAN "
    -> AttributeManager_21
AttributeManager_21
    ATTR_TABLE:
      REMOVE _clipped2
      RENAME_SET_VALUE band0.median > citygml_relative_to_water
      REMOVE CDLOG
    -> GeometryReplacer_3
GeometryReplacer_3
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> Aggregator_5
Aggregator_5
    ACCUM_ATTRS_NAME = Merge Incoming Attributes
    AGGREGATE_TYPE = Homogeneous Collection (If Possible)
    GROUP_BY = gml_id
    MODE = Geometry - Assemble One Level
    SEP = ,
    AGGREGATE -> 3DForcer_2
3DForcer_2
    KEEPZVAL = No
    ZVALATTR = @Value(citygml_relative_to_water)
    -> CityGMLGeometrySetter_6
CityGMLGeometrySetter_6
    GEOM = lod0MultiSurface
    ROLE = cityObjectMember
    -> WaterBody (writer CITYGML_3)
WaterBody (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer
WaterClosureSurface (writer CITYGML_3)
    attributes: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
WaterGroundSurface (writer CITYGML_3)
    attributes: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
WaterSurface (writer CITYGML_3)
    attributes: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

Bookmark: City Furniture
Note: TIFF
Junction_6
    -> Polygon_ZValue_from_Raster_2 [Raster_input]
Note: TIFF
Junction_8
    -> Line_ZValue_from_Raster [Raster_input]
Antena (reader ACAD_1)
    -> AttributeManager_20
AttributeManager_20
    ATTR_TABLE:
      SET_TO autocad_entity_handle = @Value(autocad_entity_handle)_@Value(fme_basename)
      SET_TO citygml_class = 1010
      SET_TO citygml_class_codeSpace = http://www.sig3d.org/codelists/standard/cityfurniture/2.0/CityFurniture_class.xml
      SET_TO citygml_function{0} = 1280
      SET_TO citygml_function{0}.codeSpace = http://www.sig3d.org/codelists/standard/cityfurniture/2.0/CityFurniture_function.xml
      SET_TO citygml_usage{0} = 1280
      SET_TO citygml_usage{0}.codeSpace = http://www.sig3d.org/codelists/standard/cityfurniture/2.0/CityFurniture_usage.xml
      SET_TO externalReference{0}.informationSystem = ftp://ftp.procempa.com.br/../CARTAS_1000/DWG/
      SET_TO externalReference{0}.externalObject.name = urn:pmpa:oid:@Value(autocad_entity_handle)
      SET_TO gml_id = gml_@UUID()
    -> Polygon_ZValue_from_Raster_2 [Polygon_Input]
Muro_Grade (reader ACAD_1)
    -> AttributeManager_18
Parada_Onibus (reader ACAD_1)
    -> Densifier
Densifier
    INTERVAL = 1
    MODE = Uniform Interval
    DENSIFIED -> GeometryCoercer_3
Note: Transform originals polilines features to poligons.
GeometryCoercer_3
    GQUERY:
      for $geom in //geometry
      where $geom/count(parent::geometry) = 0
      return number($geom/@fme_id)
    KIND = fme_polygon
    COERCED -> AttributeManager_16
AttributeManager_16
    ATTR_TABLE:
      SET_TO autocad_entity_handle = @Value(autocad_entity_handle)_@Value(fme_basename)
      SET_TO citygml_class = 1000
      SET_TO citygml_class_codeSpace = http://www.sig3d.org/codelists/standard/cityfurniture/2.0/CityFurniture_class.xml
      SET_TO citygml_function{0} = 1110
      SET_TO citygml_function{0}.codeSpace = http://www.sig3d.org/codelists/standard/cityfurniture/2.0/CityFurniture_function.xml
      SET_TO citygml_usage{0} = 1110
      SET_TO citygml_usage{0}.codeSpace = http://www.sig3d.org/codelists/standard/cityfurniture/2.0/CityFurniture_usage.xml
      SET_TO externalReference{0}.informationSystem = ftp://ftp.procempa.com.br/../CARTAS_1000/DWG/
      SET_TO externalReference{0}.externalObject.name = urn:pmpa:oid:@Value(autocad_entity_handle)
      SET_TO gml_id = gml_@UUID()
    -> Polygon_ZValue_from_Raster_2 [Polygon_Input]
Poste (reader ACAD_1)
    -> AttributeManager_17
AttributeManager_17
    ATTR_TABLE:
      SET_TO autocad_entity_handle = @Value(autocad_entity_handle)_@Value(fme_basename)
      SET_TO citygml_class = 1030
      SET_TO citygml_class_codeSpace = http://www.sig3d.org/codelists/standard/cityfurniture/2.0/CityFurniture_class.xml
      SET_TO citygml_function{0} = 1170
      SET_TO citygml_function{0}.codeSpace = http://www.sig3d.org/codelists/standard/cityfurniture/2.0/CityFurniture_function.xml
      SET_TO citygml_usage{0} = 1170
      SET_TO citygml_usage{0}.codeSpace = http://www.sig3d.org/codelists/standard/cityfurniture/2.0/CityFurniture_usage.xml
      SET_TO externalReference{0}.informationSystem = ftp://ftp.procempa.com.br/../CARTAS_1000/DWG/
      SET_TO externalReference{0}.externalObject.name = urn:pmpa:oid:@Value(autocad_entity_handle)
      SET_TO gml_id = gml_@UUID()
    -> Polygon_ZValue_from_Raster_2 [Polygon_Input]
Polygon_ZValue_from_Raster_2: ZValue_Raster
    GML_ID = @Value(gml_id)
    -> CityGMLGeometrySetter_2
    -> Junction_31
Note: VertexExtractor_2 : Input
Junction_31
    -> Junction_32
Note: Polygon_ZValue_from_Raster_2 : Output
Junction_32
    -> VertexExtractor_2
Cerca (reader ACAD_1)
    -> AttributeManager_18
AttributeManager_18
    ATTR_TABLE:
      SET_TO autocad_entity_handle = @Value(autocad_entity_handle)_@Value(fme_basename)
      SET_TO citygml_class = 1020
      SET_TO citygml_class_codeSpace = http://www.sig3d.org/codelists/standard/cityfurniture/2.0/CityFurniture_class.xml
      SET_TO citygml_function{0} = 1440
      SET_TO citygml_function{0}.codeSpace = http://www.sig3d.org/codelists/standard/cityfurniture/2.0/CityFurniture_function.xml
      SET_TO citygml_usage{0} = 1440
      SET_TO citygml_usage{0}.codeSpace = http://www.sig3d.org/codelists/standard/cityfurniture/2.0/CityFurniture_usage.xml
      SET_TO externalReference{0}.informationSystem = ftp://ftp.procempa.com.br/../CARTAS_1000/DWG/
      SET_TO externalReference{0}.externalObject.name = urn:pmpa:oid:@Value(autocad_entity_handle)
      SET_TO gml_id = gml_@UUID()
    -> Line_ZValue_from_Raster [Line_input]
Bueiro (reader ACAD_1)
    -> AttributeManager_19
AttributeManager_19
    ATTR_TABLE:
      SET_TO autocad_entity_handle = @Value(autocad_entity_handle)_@Value(fme_basename)
      SET_TO citygml_class = 1030
      SET_TO citygml_class_codeSpace = http://www.sig3d.org/codelists/standard/cityfurniture/2.0/CityFurniture_class.xml
      SET_TO citygml_function{0} = 1540
      SET_TO citygml_function{0}.codeSpace = http://www.sig3d.org/codelists/standard/cityfurniture/2.0/CityFurniture_function.xml
      SET_TO citygml_usage{0} = 1540
      SET_TO citygml_usage{0}.codeSpace = http://www.sig3d.org/codelists/standard/cityfurniture/2.0/CityFurniture_usage.xml
      SET_TO externalReference{0}.informationSystem = ftp://ftp.procempa.com.br/../CARTAS_1000/DWG/
      SET_TO externalReference{0}.externalObject.name = urn:pmpa:oid:@Value(autocad_entity_handle)
      SET_TO gml_id = gml_@UUID()
    -> Line_ZValue_from_Raster [Line_input]
Line_ZValue_from_Raster
    GML_ID = @Value(gml_id)
    -> CityGMLGeometrySetter_2
    -> Junction_29
CityGMLGeometrySetter_2
    GEOM = lod1Geometry
    ROLE = cityObjectMember
    -> CityFurniture (writer CITYGML_3)
Note: VertexExtractor_2 : Input
Junction_29
    -> Junction_30
Note: Line_ZValue_from_Raster : Output
Junction_30
    -> VertexExtractor_2
VertexExtractor_2
    Point -> Junction_33
Note: SurfaceModeller : Points/Lines
Junction_33
    -> Junction_34

Bookmark: Vegetation
Note: TIFF
Junction_10
    -> Polygon_ZValue_from_Raster [Raster_input]
Note: TIFF
Junction_12
    -> Polygon_ZValue_from_Raster_3 [Raster_input]
Arvores_Isoladas (reader ACAD_1)
    -> AttributeManager_24
AttributeManager_24
    ATTR_TABLE:
      SET_TO gml_id = gml_@UUID()
      SET_TO autocad_entity_handle = @Value(autocad_entity_handle)_@Value(fme_basename)
      SET_TO citygml_class = 1020
      SET_TO citygml_class_codeSpace = http://www.sig3d.org/codelists/standard/vegetation/2.0/SolitaryVegetationObject_class.xml
      SET_TO citygml_function{0} = 1020
      SET_TO citygml_function{0}.codeSpace = http://www.sig3d.org/codelists/standard/vegetation/2.0/SolitaryVegetationObject_function.xml
      SET_TO citygml_usage{0} = 1020
      SET_TO citygml_usage{0}.codeSpace = http://www.sig3d.org/codelists/standard/vegetation/2.0/SolitaryVegetationObject_usage.xml
      SET_TO externalReference{0}.informationSystem = ftp://ftp.procempa.com.br/../CARTAS_1000/DWG/
      SET_TO externalReference{0}.externalObject.name = urn:pmpa:oid:@Value(autocad_entity_handle)
    -> Polygon_ZValue_from_Raster [Polygon_Input]
Polygon_ZValue_from_Raster: ZValue_Raster
    GML_ID = @Value(gml_id)
    -> CityGMLGeometrySetter_3
    -> Junction_37
CityGMLGeometrySetter_3
    GEOM = lod1Geometry
    ROLE = cityObjectMember
    -> SolitaryVegetationObject (writer CITYGML_3)
Note: VertexExtractor_3 : Input
Junction_37
    -> Junction_38
Note: Polygon_ZValue_from_Raster : Output
Junction_38
    -> VertexExtractor_3
VertexExtractor_3
    Point -> Junction_39
Note: SurfaceModeller : Points/Lines
Junction_39
    -> Junction_40
Vegetacao (reader ACAD_1)
    -> AreaBuilder_3
AreaBuilder_3
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    AREA -> AttributeCreator_11
AttributeCreator_11
    ATTR_TABLE:
      SET_TO gml_id = gml_@UUID()
      SET_TO citygml_class = 9999
      SET_TO citygml_class_codeSpace = http://www.sig3d.org/codelists/standard/vegetation/2.0/PlantCover_class.xml
      SET_TO citygml_function{0} = 9999
      SET_TO citygml_function{0}.codeSpace = http://www.sig3d.org/codelists/standard/vegetation/2.0/PlantCover_function.xml
      SET_TO citygml_usage{0} = 9999
      SET_TO citygml_function{0}.codeSpace = http://www.sig3d.org/codelists/standard/vegetation/2.0/PlantCover_usage.xml
      SET_TO externalReference{0}.informationSystem = ftp://ftp.procempa.com.br/../CARTAS_1000/DWG/
      SET_TO externalReference{0}.externalObject.name = urn:pmpa:oid:@Value(autocad_entity_handle)
    -> Polygon_ZValue_from_Raster_3 [Polygon_Input]
Polygon_ZValue_from_Raster_3: ZValue_Raster
    GML_ID = @Value(gml_id)
    -> CityGMLGeometrySetter_5
CityGMLGeometrySetter_5
    GEOM = lod1MultiSurface
    ROLE = cityObjectMember
    -> PlantCover (writer CITYGML_3)

Bookmark: LOD0-Footprint
Note: Create specific CityGML Attributes to LOD0Footprint
CityGMLGeometrySetter
    GEOM = lod0FootPrint
    ROLE = cityObjectMember
    -> Aggregator_3

Bookmark: remove duplicated parts from solids
Deaggregator_2
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten One Level
    PART_NUMBER_FIELD = _part_number
    SPLIT_COMPOSITES = Yes
    DEAGGREGATED -> Matcher
Matcher
    BLANK_AND_MISSING_NAMES_TRAITS_DIFFER = No
    CHECK_COORDINATE_SYSTEMS = No
    CNT_ATTR = _match_id
    LENIENT_MATCH = Yes
    MATCH = FULL
    SINGLE_MATCHED -> Extruder_2
    NOT_MATCHED -> Extruder_2

Bookmark: LoD1 - Solid
Extruder_2
    DIRECTION = Vertical
    DISTANCE = @Value(citygml_measured_height)-@Value(citygml_relative_to_water)
    EXTRUDED -> GeometryCoercer_4
    EXTRUDED -> CityGMLGeometrySetter_9
Note: Create specific CityGML Attributes to LOD1Solid
CityGMLGeometrySetter_9
    GEOM = lod1Solid
    ROLE = cityObjectMember
    -> GeometryCoercer
Note: fme brep solid
GeometryCoercer
    GQUERY:
      for $geom in //geometry
      where $geom/count(parent::geometry) = 0
      return number($geom/@fme_id)
    KIND = fme_brep_solid
    COERCED -> GeometryPropertySetter_3
GeometryPropertySetter_3
    OVERWRITE_CHOICE = Yes
    REMOVE_ATTRIBUTE = No
    SETTYPE_PARAM = Traits From Attributes
    SRC_ATTRS = citygml_lod_name
    SET -> Aggregator_3

Bookmark: Turn solids into composite surfaces and deaggregate them
GeometryCoercer_4
    GQUERY:
      for $geom in //geometry
      where $geom/count(parent::geometry) = 0
      return number($geom/@fme_id)
    KIND = fme_composite_surface
    COERCED -> Deaggregator_3
Deaggregator_3
    COPY_ATTR = Every Node
    EXPLODE_INSTANCES = Yes
    ID_ATTR = _hierarchy_id
    ID_SELECTION = ID and Parent ID
    LIST_ATTR_MODE_LOOKUP = LEAN
    MODE = Preserve Hierarchy
    PARENT_ID_ATTR = _hierarchy_parent_id
    SPLIT_COMPOSITES = Yes
    DEAGGREGATED -> CoordinateRounder_2

Bookmark: LoD2
CoordinateRounder_2
    XPREC = 2
    YPREC = 2
    ZPREC = 2
    ROUNDED -> PlanarityFilter_3
Note: Identify walls, roof surface and ground surface based on surfaceNormalZ attribute
PlanarityFilter_3
    ANGULAR_TOLERANCE_CHOICE = Automatic
    OUTPUT_NORMAL = Yes
    THICKNESS_TOLERANCE_CHOICE = Automatic
    PLANAR -> AttributeRangeFilter_2
AttributeRangeFilter_2
    IN_ATTR = _surfaceNormalZ
    LUT = -0.2,0.2,wall,-1.2,-0.8,ground,0.8,1.2,roof
    wall -> SurfaceOnSurfaceOverlayer [SURFACE]
    ground -> AttributeManager_31
    roof -> AttributeManager_31
Note: Generalize non-shared surfaces
dissolver: SurfaceDissolver
    ACCUM_INPUT_ATTRS = Use Attributes From One Feature
    DEAGGREGATE_INPUT = Yes
    MATCHING_APPS = No
    NORMAL_TOLERANCE = 1
    OFFSET_TOLERANCE = 0
    SEPARATE_SURFACES = No
    SURFACE -> AttributeManager_11
AttributeManager_31
    ATTR_TABLE = SET_TO surface_parent_id{0}.gml_id = @Value(gml_id)
    -> AttributeManager_11
Note: Sets surfaces ID
AttributeManager_11
    ATTR_TABLE:
      SET_TO gml_id = gml_@UUID()
      REMOVE _geometry_name
      REMOVE _part_number
      REMOVE _match_id
      SET_TO gml_id_surface = #@Value(gml_id)
    -> AttributeCreator_3
AttributeCreator_3
    ATTR_TABLE = SET_TO citygml_lod_name = lod2MultiSurface
    -> GeometryPropertySetter_4
GeometryPropertySetter_4
    OVERWRITE_CHOICE = Yes
    REMOVE_ATTRIBUTE = No
    SETTYPE_PARAM = Traits From Attributes
    SRC_ATTRS = citygml_lod_name
    SET -> GeometryPropertySetter_6
GeometryPropertySetter_6
    GQUERY:
      for $geom in //geometry
      where $geom/@fme_geometry_type = 'IFMEPolygon'
      or $geom/@fme_geometry_type = 'IFMEDonut'
      return number($geom/@fme_id)
    OVERWRITE_CHOICE = Yes
    REMOVE_ATTRIBUTE = No
    SETTYPE_PARAM = Traits From Attributes
    SRC_ATTRS = gml_id
    SET -> AttributeManager_26
    SET -> GeometryPropertyRemover
GeometryPropertyRemover
    REMOVETYPE_PARAM = Traits
    REMOVE_ALL = Yes
    REMOVED -> AttributeCreator_4
AttributeCreator_4
    ATTR_TABLE:
      SET_TO citygml_lod_name = lod2Solid
      SET_TO xlink_href = @Value(gml_id)
    -> GeometryPropertySetter_8
GeometryPropertySetter_8
    OVERWRITE_CHOICE = Yes
    REMOVE_ATTRIBUTE = Yes
    SETTYPE_PARAM = Traits From Attributes
    SRC_ATTRS = xlink_href
    SET -> AttributeManager_27
    SET -> AttributeManager_28
AttributeManager_26
    ATTR_TABLE:
      REMOVE gml_id
      SET_TO gml_parent_id = (@Value(surface_parent_id{0}.gml_id) @Value(surface_parent_id{1}.gml_id))
      SET_TO citygml_feature_role = boundedBy
    -> PlanarityFilter_2
Note: Identify walls, roof surface and ground surface based on surfaceNormalZ attribute
PlanarityFilter_2
    ANGULAR_TOLERANCE_CHOICE = Automatic
    OUTPUT_NORMAL = Yes
    THICKNESS_TOLERANCE_CHOICE = Automatic
    PLANAR -> AttributeRangeFilter
    NOT_PLANAR -> AttributeRangeFilter
AttributeRangeFilter
    IN_ATTR = _surfaceNormalZ
    LUT = -0.2,0.2,wall,-1.2,-0.8,ground,0.8,1.2,roof
    wall -> WallSurface (writer CITYGML_3)
    ground -> GroundSurface (writer CITYGML_3)
    roof -> RoofSurface (writer CITYGML_3)
WallSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
GroundSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
RoofSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
SurfaceBuilder
    DROP_HOLES = No
    ENABLE_TOLERANCE = Yes
    HOLE_ATTR = _is_hole
    HOLE_LIST_ATTRS_TO_INCLUDE = gml_id
    HOLE_LIST_ATTRS_TO_INCLUDE_MODE = Selected Attributes
    HOLE_LIST_NAME = surface_parent_id
    NORMAL_TOLERANCE = 0.1
    OFFSET_TOLERANCE = 0.1
PlanarityFilter
    ANGULAR_TOLERANCE = 30
    ANGULAR_TOLERANCE_CHOICE = Custom
    OUTPUT_NORMAL = No
    THICKNESS_TOLERANCE = 100
    THICKNESS_TOLERANCE_CHOICE = Custom

Bookmark: check which of the surfaces are shared by 2 buildings
Note: Also generates a list with the solid's ID to which the surfaces belonged ("parent ID")
SurfaceOnSurfaceOverlayer
    ACCUM_ATTRS_NAME = Use Attributes From One Feature
    DEAGGREGATE_INPUT = Yes
    ENABLE_TOLERANCE = Yes
    LIST_ATTRS_TO_INCLUDE = gml_id
    LIST_NAME = surface_parent_id
    NORMAL_TOLERANCE = 0.1
    OFFSET_TOLERANCE = 0.1
    OVC_ATTR = _overlaps
    SURFACE -> AttributeFilter_4
AttributeFilter_4
    ATTR_NAME = _overlaps
    ATTR_VALUES = <Empty>,<Missing>,<Null>,<Unfiltered>,1,2
    1 -> dissolver
    2 -> AttributeManager_11

Bookmark: aggregate to Building level and assign trait properties (citygml_lod_name)
AttributeManager_27
    ATTR_TABLE = SET_TO gml_id = @Value(surface_parent_id{0}.gml_id)
    -> Aggregator_9
AttributeManager_28
    ATTR_TABLE = SET_TO gml_id = @Value(surface_parent_id{1}.gml_id)
    -> Aggregator_9
Aggregator_9
    ACCUM_ATTRS_NAME = Merge Incoming Attributes
    AGGREGATE_TYPE = Homogeneous Collection (If Possible)
    GROUP_BY = gml_id
    MODE = Geometry - Assemble One Level
    SEP = ,
    AGGREGATE -> Tester_10
Tester_10
    BOOL_OP = OR
    COMPOSITE_TEST = 1
    TEST_CLAUSE = TEST gml_id ATTRIBUTE_HAS_A_VALUE ""
    TEST_MODE = TEST
    PASSED -> GeometryCoercer_5
GeometryCoercer_5
    GQUERY:
      for $geom in //geometry
      where $geom/count(parent::geometry) = 0
      return number($geom/@fme_id)
    KIND = fme_brep_solid
    COERCED -> GeometryPropertySetter_9
GeometryPropertySetter_9
    OVERWRITE_CHOICE = Yes
    REMOVE_ATTRIBUTE = No
    SETTYPE_PARAM = Traits From Attributes
    SRC_ATTRS = citygml_lod_name
    SET -> Aggregator_3

Bookmark: Bridge
Ponte (reader ACAD_1)
Bridge (writer CITYGML_3)
    attributes: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
BridgeConstructionElement (writer CITYGML_3)
    attributes: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
BridgeFurniture (writer CITYGML_3)
    attributes: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
BridgeInstallation (writer CITYGML_3)
    attributes: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
BridgePart (writer CITYGML_3)
    attributes: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
BridgeRoom (writer CITYGML_3)
    attributes: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
IntBridgeInstallation (writer CITYGML_3)
    attributes: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

Bookmark: LandUse
Campo_de_Fut_Quad_de_Esp (reader ACAD_1)
Topon_Campo_de_Fut_Quad_de_Esp (reader ACAD_1)
LandUse (writer CITYGML_3)
    attributes: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

Bookmark: CityObjectGroup
CityObjectGroup (writer CITYGML_3)
    attributes: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

Bookmark: Tunnel
HollowSpace (writer CITYGML_3)
    attributes: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
IntTunnelInstallation (writer CITYGML_3)
    attributes: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
Tunnel (writer CITYGML_3)
    attributes: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
TunnelFurniture (writer CITYGML_3)
    attributes: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
TunnelInstallation (writer CITYGML_3)
    attributes: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
TunnelPart (writer CITYGML_3)
    attributes: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

Bookmark: Generic
GenericCityObject (writer CITYGML_3)
    attributes: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

Bookmark: Amsterdam
Bridge (reader CITYGML_2)
    attributes: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
CityModel (reader CITYGML_2)
    attributes: citygml_target_uri xml_buffer, gml_description xml_buffer, gml_name xml_buffer, citygml_city_object_member{}.xlink_href xml_buffer, citygml_appearance_member{}.xlink_href xml_buffer, gml_feature_member{}.xlink_href xml_buffer
GenericCityObject (reader CITYGML_2)
    attributes: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
LandUse (reader CITYGML_2)
    attributes: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
PlantCover (reader CITYGML_2)
    attributes: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
Road (reader CITYGML_2)
    attributes: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
WaterBody (reader CITYGML_2)
    attributes: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

FME custom transformer OSMDownloader
Downloads OpenStreetMap (OSM) data file corresponding to specified extents. You can read features from the downloaded file with the OpenStreetMap (OSM) XML [OSM] reader.
    Note: Depending on the extents, the data size could become too large and it may take too long time to complete downloading. To prevent downloading too large data, this transformer limits the width and height of the extents to 
    0.15 x 0.15 degrees
    (9 x 9 minutes). If the width or height of the specified extents was larger than the limit, the input feature would be immediately output from the 
    <Rejected>
    port. See also the description about the related parameters.
Parameters 
    Extents Minimum X/Y, Maximum X/Y (degrees): 
    Specify the extents in decimal degrees. The extents should satisfy all of these conditions. 
    -180 <= xmin, xmax <= 180 
    -90 <= ymin, ymax <= 90 
    xmin is west than xmax, ymin is south than ymax
    width <= 0.15, height <= 0.15 
    If one of the conditions wasn't satisfied, the input feature would be immediately output from the <Rejected>
    port. 
    Output OSM File Path: 
    Specify a file path for saving the downloaded OSM file. 
    Output OSM File Path Attribute: 
    Optionally specify an attribute name which stores the saved OSM file path. Value of the attribute will be the same as the file path specified to the "Output OSM File Path" parameter. 
    HTTP Connection Timeout Length (seconds): 
    This parameter can be used to set a timeout on HTTP connection requests. If a connection to the server cannot be created within the given number of seconds, the request will fail, and the feature will be output through the Failure
    port. The default connection timeout is 60 seconds. If 0 is entered, there will be no timeout, and the transformer will wait indefinitely for a successful connection. 
    HTTP Transfer Timeout Length (seconds): 
    This parameter can be used to set a timeout on HTTP transfers. If data stops being transferred for more than the given number of seconds, the request will fail, and the feature will be output through the Failure
    port. The default transfer timeout is 300 seconds. If 0 is entered, there will be no timeout, and the transformer will wait indefinitely for data to resume being transferred. 
    Overpass API Endpoint URL:
    Set a public Overpass API endpoint URL. Available URLs are listed here: 
        https://wiki.openstreetmap.org/wiki/Overpass_API

Parameters:
- BB_XMIN =   # Extents Minimum X (degrees)
- BB_YMIN =   # Extents Minimum Y (degrees)
- BB_XMAX =   # Extents Maximum X (degrees)
- BB_YMAX =   # Extents Maximum Y (degrees)
- OUTPUT_FILENAME =   # Output OSM File Path
- FILE_PATH_ATTR = _osm_file_path   # TYPE:varchar(200) Output OSM File Path Attribute
- CONNECTION_TIMEOUT_LENGTH = 60   # HTTP Connection Timeout Length (seconds)
- TRANSFER_TIMEOUT_LENGTH = 300   # HTTP Transfer Timeout Length (seconds)
- OVERPASS_URL = https://lz4.overpass-api.de/api/interpreter   # Overpass API Endpoint URL
- BB_MAX_WIDTH = 0.15   # Bounding Box Maximum Width (degrees)
- BB_MAX_HEIGHT = 0.15   # Bounding Box Maximum Height (degrees)

Input (input)
    -> AttributeCreator
Note: Create Overpass QL
StringConcatenator
    ACTION = Create New Attribute
    PARM_LINE = (node($(BB_YMIN),$(BB_XMIN),$(BB_YMAX),$(BB_XMAX));<;);out meta;
    VAL_ATTR = __osmdownloader.ql
    -> HTTPCaller
Note: Download and save an OSM file.
HTTPCaller
    ADDITIONAL_URL_PARAMETERS = data;@Value(__osmdownloader.ql)
    CONNECTION_TIMEOUT_LENGTH = $(CONNECTION_TIMEOUT_LENGTH)
    ERROR_ATTR = _error
    FILE_PATH_ATTR = $(FILE_PATH_ATTR)
    FOLLOW_REDIRECTS = Yes
    HTTP_METHOD = GET
    OUTPUT_FILENAME = $(OUTPUT_FILENAME)
    RESPONSE_HEADER_LIST_ATTR = _headers
    SAVE_FILE = File
    SAVE_MULTI = No
    STATUS_CODE_ATTR = _http_status_code
    TARGET_URL = $(OVERPASS_URL)
    TRANSFER_TIMEOUT_LENGTH = $(TRANSFER_TIMEOUT_LENGTH)
    USE_COOKIES = No
    VERIFY_SSL_CERTIFICATES = Yes
    -> AttributeRemover
    <REJECTED> -> TclCaller_2
AttributeRemover
    REMOVE_ATTRS = __osmdownloader.file_path,__osmdownloader.folder_exists,__osmdownloader.ql,__osmdownloader.xmax
    -> Success (output)
Success (output)
TclCaller_2
    TCLPROG = file delete [FME_GetAttribute "__osmdownloader.file_path"]
    VAL_ATTR = __osmdownloader.file_path
    -> AttributeRemover_2
AttributeRemover_2
    REMOVE_ATTRS = __osmdownloader.file_path,__osmdownloader.folder_exists,__osmdownloader.ql,__osmdownloader.xmax
    -> Failure (output)
Failure (output)
AttributeRemover_3
    REMOVE_ATTRS = __osmdownloader.file_path,__osmdownloader.folder_exists,__osmdownloader.xmax
    -> <Rejected> (output)
<Rejected> (output)

Bookmark: Make destination folder; Validate specified extents
AttributeCreator
    ATTR_LIST = __osmdownloader.xmax,"FME_CONDITIONAL:DEFAULT_VALUE'$(BB_XMAX)'BOOL_OP;AND;COMPOSITE_TEST;<Unused>;TEST $(BB_XMAX) < 0;TEST $(BB_XMIN) > 0'@Evaluate(360+$(BB_XMAX))'FME_NUM_CONDITIONS2___",__osmdownloader.file_path,$(OUTPUT_FILENAME)
    -> TclCaller
TclCaller
    SRC:
      proc createDirectory {} {
          set dir [file dirname [file normalize [FME_GetAttribute "__osmdownloader.file_path"]]]
          if {![file exists $dir]} {
              file mkdir $dir
          }
          return [file exists $dir]
      }
    TCLPROG = createDirectory
    VAL_ATTR = __osmdownloader.folder_exists
    -> Tester
Tester
    BOOL_OP = AND
    TEST_CLAUSE:
      TEST -180 <= $(BB_XMIN)
      TEST $(BB_XMAX) <= 180
      TEST -90 <= $(BB_YMIN)
      TEST $(BB_YMAX) <= 90
      TEST $(BB_XMIN) < @Value(__osmdownloader.xmax)
      TEST $(BB_YMIN) < $(BB_YMAX)
      TEST @Evaluate(@Value(__osmdownloader.xmax)-$(BB_XMIN)) < @Evaluate($(BB_MAX_WIDTH)+1.0e-8)
      TEST @Evaluate($(BB_YMAX)-$(BB_YMIN)) < @Evaluate($(BB_MAX_HEIGHT)+1.0e-8)
    TEST_MODE = Automatic
    PASSED -> StringConcatenator
    FAILED -> AttributeRemover_3

FME custom transformer ZValue_Raster
Intersect polygon data to extract Z values from it

Parameters:
- GML_ID = @Value(gml_id)   # Gml Id

Polygon_Input (input)
    -> GeometryExtractor_3
GeometryExtractor_3
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> Clipper_4 [CLIPPER]
Raster_input (input)
    -> Clipper_4 [CLIPPEE]
Clipper_4
    ATTR_ACCUM_MODE = Merge Clipper
    ATTR_CONFLICT_RES = Use Clipper
    BOUNDARY_CASES = Treat as Inside
    CLEANING_TOLERANCE = 20
    CLIPPED_ATTR = _clipped2
    CLIP_TYPE = Multiple Clippers
    CONNECT_Z_MODE = First Wins
    LINES_AS_SEGMENTS = Yes
    MEASURE_TYPE = Continuous
    MISSING_VAL_MODE = Compute
    PRESERVE_CLIPPEE_EXTENTS = No
    VAL_SOURCE = Clipper and Clippee
    INSIDE -> RasterStatisticsCalculator_3
RasterStatisticsCalculator_3
    RASTER_LEVEL = BAND_ONLY
    RASTER_STATS = "0       MEDIAN "
    -> AttributeManager_23
AttributeManager_23
    ATTR_TABLE = RENAME_SET_VALUE band0.median > citygml_relative_to_water
    -> GeometryReplacer_4
GeometryReplacer_4
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> Aggregator_6
Aggregator_6
    ACCUM_ATTRS_NAME = Merge Incoming Attributes
    AGGREGATE_TYPE = Homogeneous Collection (If Possible)
    GROUP_BY = gml_id
    MODE = Geometry - Assemble One Level
    SEP = ,
    AGGREGATE -> 3DForcer_6
3DForcer_6
    KEEPZVAL = No
    ZVALATTR = @Value(citygml_relative_to_water)
    -> Output (output)
Output (output)

FME custom transformer Line_ZValue_from_Raster
Intersect a line with a raster to extract Zvalue from it

Parameters:
- GML_ID = @Value(gml_id)   # Gml Id

Line_input (input)
    -> Densifier
Densifier
    INTERVAL = 1
    MODE = Uniform Interval
    DENSIFIED -> Chopper
Chopper
    DEAGGREGATE_INPUT = Deaggregate
    MAX_VERTICES = 1
    MODE = By Vertex
    REMNANT_ATTR = _remnant
    CHOPPED -> PointOnRasterValueExtractor [POINT]
Raster_input (input)
    -> PointOnRasterValueExtractor [RASTER]
PointOnRasterValueExtractor
    INTERPOLATION_TYPE_NAME = Nearest Neighbor
    POINT -> 3DForcer_5
3DForcer_5
    KEEPZVAL = No
    ZVALATTR = @Value(_band{0}.value)
    -> LineBuilder_2
LineBuilder_2
    ACCUM_INPUT_ATTRS = Use Attributes From One Feature
    GROUP_BY = gml_id
    REMOVE_DUPLICATES = Yes
    LINE -> AttributeManager_21
    POLYGON -> GeometryCoercer_5
GeometryCoercer_5
    GQUERY:
      for $geom in //geometry
      where $geom/count(parent::geometry) = 0
      return number($geom/@fme_id)
    KIND = fme_line
    COERCED -> AttributeManager_21
AttributeManager_21
    ATTR_TABLE = SET_TO citygml_relative_to_water = @Value(_band{0}.value)
    -> Output (output)
Output (output)
